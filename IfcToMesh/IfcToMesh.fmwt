FME workspace IfcToMesh.fmwt
Title: IfcToMesh

Parameters:
- SourceDataset_IFC = $(FME_MF_DIR)dataset.ifc   # Source Industry Foundation Class (IFC) File(s)
- FEATURE_TYPES =

Readers:
- IFC_1: IFC from $(SourceDataset_IFC)

Note: Expose fme_dataset on the reader
PropertySetDefinition (reader IFC_1)
    attributes: CompositionType enumeration, BuildingAddress.PostalBox string, ElevationOfTerrain real, BuildingAddress.Purpose enumeration, ifc_properties{}.data_type string, SiteAddress.Town string, BuildingAddress.InternalLocation string, ObjectType string, SiteAddress.Purpose enumeration, LongName string, InteriorOrExteriorSpace enumeration, SiteAddress.UserDefinedPurpose string, BuildingAddress.Town string, ElevationWithFlooring real, Elevation real, Name string, ifc_properties{}.name string, SiteAddress.Region string, BuildingAddress.Region string, RefLatitude real, ifc_property_set_name string, Axis geometry, Body geometry, OverallHeight real, ElevationOfRefHeight real, PredefinedType enumeration, BuildingAddress.AddressLines string, BuildingAddress.UserDefinedPurpose string, BuildingAddress.Description string, BuildingAddress.PostalCode string,
      SiteAddress.InternalLocation string, SiteAddress.Country string, SiteAddress.Description string, RefElevation real, RefLongitude real, ifc_properties{}.property_type string, SiteAddress.AddressLines string, LandTitleNumber string, Tag string, SiteAddress.PostalCode string, BuildingAddress.Country string, GlobalId char(22), ShapeType enumeration, OverallWidth real, Description string, Phase string, SiteAddress.PostalBox string
    -> IfcToMesh [IFC_File]
IfcToMesh
    Temp = $(FME_MF_DIR)1/IFCconvert/temp
    Include = IfcBuildingElementPart IfcColumn IfcCovering IfcCurtainWall IfcDoor IfcMember IfcPlate IfcRoof IfcSlab IfcWall IfcWallStandardCase IfcWindow
    Deflection-Tolerance = 0.001
    IFCconvert = $(FME_MF_DIR)1/IFCconvert/ifc convert
    Precision = 15
    Include_attributes = Yes
    Mesh -> IfcToMesh_Mesh
IfcToMesh_Mesh: Inspector

FME custom transformer IfcToMesh
Script converting IFC files to 3D meshes. The scripts are developed in the FME (Feature Manipulation Engine) version 2017.1(Build 17539).
This workspace is released under the 3-Clause BSD License. For details, see https://opensource.org/licenses/BSD-3-Clause
Copyright (c) 2018, Luleå University of Technology and Lund University 
All rights reserved. 
Documentation available at : https://github.com/TestbedLU/Testbed_BIM_GIS

Parameters:
- Temp = $(FME_MF_DIR)1/IFCconvert/temp
- IFCconvert = $(FME_MF_DIR)1/IFCconvert/ifc convert
- Include_attributes = No   # Include attributes
- DisableOpeningsubtractions =   # Yes,--disable-opening-subtractions %No, Disable Opening Subtractions
- World_coords =   # Yes,--use-world-coords %No, Use World Coordinates
- Convert_Back_Units =   # Yes,--convert-back-units %No, Convert Back Units
- Plan =   # Yes,--plan %No, Plan
- Model =   # Yes,--model %No, Model
- Weld-Vertices =   # Yes,--weld-vertices %No, Weld Vertices
- Sew_shells =   # Yes,--sew-shells %No, Sew shells
- Enable-layerset-slicing =   # Yes,--enable-layerset-slicing %No, Enable Layerset Slicing
- Generate_Uvs =   # Yes,--generate-uvs %No, Generate Uvs
- Deflection-Tolerance = 0.001   # Deflection Tolerance
- No_normals =   # Yes,--no-normals %No, No normals
- Precision = 15
- LISTBOX = IfcBuildingElementPart IfcColumn IfcCovering IfcCurtainWall IfcDoor IfcMember IfcPlate IfcRoof IfcSlab IfcWall IfcWallStandardCase IfcWindow

IFC_File (input)
    -> AttributeExposer
Note: Expose FME_dataset path
AttributeExposer
    ATTR_LIST = fme_dataset,GlobalId
    -> Tester
Note: Test if FME_dataset path exsists
Tester
    TEST_MODE = Automatic
    TEST_CLAUSE = TEST @Value(fme_dataset) ATTRIBUTE_HAS_VALUE ""
    BOOL_OP = OR
    TEST_DESCRIPTION = ""
    PASSED -> DuplicateFilter_2
    PASSED -> Tester_3
    FAILED -> Terminator
Tester_3
    TEST_MODE = Automatic
    TEST_CLAUSE = TEST $(Include_attributes) = Yes
    BOOL_OP = OR
    TEST_DESCRIPTION = ""
    PASSED -> FeatureMerger [SUPPLIER]
Note: User wants attributes of / IFC objects?
Tester_2
    TEST_MODE = Automatic
    TEST_CLAUSE = TEST $(Include_attributes) = Yes
    BOOL_OP = OR
    TEST_DESCRIPTION = ""
    PASSED -> Deaggregator
    FAILED -> AttributeRemover
Note: Merge back the attributes to the new 3D model(mesh)
FeatureMerger
    ATTR_CONFLICT_RES = Use Requestor
    REJECT_NULL_MISSING_KEYS = No
    ATTR_ACCUM_MODE = Merge Supplier
    MERGE_TYPE = Attributes Only
    JOIN_KEYS = @Value(obj_group) @Value(GlobalId) AUTO
    PROCESS_DUPS = No
    SUPPLIERS_FIRST = No
    IGNORE_NULLS = No
    MERGED -> AttributeRemover
AttributeRemover
    REMOVE_ATTRS = ID,Coordsys,obj_group,_count,_matched_records,LoadIfcConvertResult,_part_number,_geometry_name,Enitities,Parameters
    -> Mesh (output)
Mesh (output)
Terminator
    MESSAGE = FME DATASET NEEDS A VALUE

Bookmark: Create command for IFCconverter
DuplicateFilter_2
    INPUT_ORDERED_CHOICE = No
    KEYATTR = fme_dataset
    UNIQUE -> UUIDGenerator
Note: Generate unique ids
UUIDGenerator
    UUID_ATTR = ID
    -> AttributeKeeper
AttributeKeeper
    KEEP_ATTRS = ID,fme_dataset,Command
    -> Counter
Counter
    CNT_ATTR = _count
    START = 0
    DOMAIN = counter
    SCOPE = Global
    -> CoordinateSystemExtractor
Note: Extract coordinate system
CoordinateSystemExtractor
    CRDSYS_ATTR = Coordsys
    -> AttributeCreator
Note: Set entities and parameters
AttributeCreator
    ATTR_TABLE:
      SET_TO Enitities = --include=entities $(Include)
      SET_TO Parameters = $(DisableOpeningsubtractions)$(World_coords)$(Convert_Back_Units)$(Model)$(Plan)$(Sew_shells)$(Weld-Vertices)$(No_normals)
    -> Tester_4
Note: Remove entitites if no entities is selected
Tester_4
    TEST_MODE = Automatic
    TEST_CLAUSE = TEST @Value(Enitities) = --include=entities
    BOOL_OP = OR
    TEST_DESCRIPTION = ""
    PASSED -> AttributeCreator_4
    FAILED -> SystemCaller
AttributeCreator_4
    ATTR_TABLE = SET_TO Enitities =
    -> SystemCaller
SystemCaller
    CMD = ""$(IFCconvert)\ifcconvert.exe" @Value(Enitities) @Value(Parameters) --use-element-guids --deflection-tolerance $(Deflection-Tolerance) --precision $(Precision) "@Value(fme_dataset)" "$(Temp)\@Value(ID).obj""
    -> AttributeCreator_3

Bookmark: Load Objfile from IFCconverter
Note: Create load path and fix path
AttributeCreator_3
    ATTR_TABLE = SET_TO LoadIfcConvertResult = $(Temp)\@Value(ID).obj
    -> StringReplacer
StringReplacer
    REPLACE_TEXT = \
    NO_MATCH = _FME_NO_OP_
    FIND_TEXT = /
    CASE = NO
    REGEXP = NO
    SRC_ATTRS = LoadIfcConvertResult
    -> FeatureReader_2 [INITIATOR]
FeatureReader_2
    COMBINE_GEOM = Use Result
    OBJ_MOVE_TO_WORLD_COORDSYS = Yes
    FORMAT = OBJ
    ATTR_ACCUM_MODE = Only Use Result
    DATASET = @Value(LoadIfcConvertResult)
    INTERACT = <No Spatial Filter>
    OUTPUT_FEATURES_DISPLAY = Schema and Data Features
    OBJ_VARIABLE_FEATURE_TYPES = yes
    OBJ_MERGE_MESH_PARTS = No
    OBJ_USE_SEARCH_ENVELOPE = NO
    <OTHER> -> AttributeExposer_3
    INITIATOR -> FeatureMerger_2 [SUPPLIER]
AttributeExposer_3
    ATTR_LIST = fme_feature_type
    -> FeatureMerger_2 [REQUESTOR]
Note: Join back information such as coordinate system from orginal file
FeatureMerger_2
    ATTR_CONFLICT_RES = Use Requestor
    REJECT_NULL_MISSING_KEYS = No
    ATTR_ACCUM_MODE = Merge Supplier
    MERGE_TYPE = Attributes Only
    JOIN_KEYS = @Value(fme_feature_type) @Value(ID) AUTO
    PROCESS_DUPS = No
    SUPPLIERS_FIRST = No
    IGNORE_NULLS = No
    MERGED -> CoordinateSystemSetter
Note: Set Coordinate system
CoordinateSystemSetter
    COORDSYS = @Value(Coordsys)
    -> Tester_2

Bookmark: Extract UUID from traits(3D)
Deaggregator
    SPLIT_COMPOSITES = No
    GEOM_NAME_FIELD = _geometry_name
    LIST_ATTR_MODE_LOOKUP = LEAN
    PART_NUMBER_FIELD = _part_number
    MODE = Flatten One Level
    EXPLODE_INSTANCES = No
    DEAGGREGATED -> GeometryPropertyExtractor
Note: Extract attributes from each 3D object
GeometryPropertyExtractor
    EXTRACTTYPE_PARAM = Traits
    TRAIT_ATTR_LIST = obj_group,No
    PREFIX_EXTRACTED_TRAITS = No
    EXTRACTED -> AttributeExposer_2
AttributeExposer_2
    ATTR_LIST = obj_group
    -> AttributeRemover_2
AttributeRemover_2
    REMOVE_ATTRS = fme_feature_type
    -> FeatureMerger [REQUESTOR]
