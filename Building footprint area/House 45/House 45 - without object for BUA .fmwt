FME workspace House 45 - without object for BUA .fmwt
Title: House 45 - without object for BUA

Parameters:
- SourceDataset_IFC = $(FME_MF_DIR)180430 - House 45.ifc   # Source Industry Foundation Class (IFC) File(s)

Readers:
- IFC_1: IFC from $(SourceDataset_IFC)

IfcSlab (reader IFC_1)
    attributes: GlobalId char(22), Name string, Description string, ObjectType string, Tag string, PredefinedType enumeration, Axis geometry, Body geometry, Box geometry, FootPrint geometry
    -> FootprintAreaCalculator [IfSlab_Input]
    -> IfcSlab_-__FootprintAreaCalculator_IfSlab_Input
IfcBuildingStorey (reader IFC_1)
    attributes: GlobalId char(22), Name string, Description string, ObjectType string, LongName string, CompositionType enumeration, Elevation real, Axis geometry, Body geometry, Box geometry, FootPrint geometry
    -> FootprintAreaCalculator [BuildingStorey_AggregatedList]
IfcWallStandardCase (reader IFC_1)
    attributes: GlobalId char(22), Name string, Description string, ObjectType string, Tag string, Axis geometry, Body geometry, Box geometry, FootPrint geometry
    -> FootprintAreaCalculator [Clipper_BottomEdge_Input]
    -> IfcSlab_-__FootprintAreaCalculator_IfSlab_Input
IfcSlab_-__FootprintAreaCalculator_IfSlab_Input: Junction
    -> FootprintAreaCalculator [All_ListBasedFeatureMerger]
    -> FootprintAreaCalculator [Clipper_Max_3m_Input]
    -> FootprintAreaCalculator [Clipper_Max_5m_Input]
IfcRoof (reader IFC_1)
    attributes: GlobalId char(22), Name string, Description string, ObjectType string, Tag string, ShapeType enumeration, Axis geometry, Body geometry, Box geometry, FootPrint geometry
    -> FootprintAreaCalculator [Clipper_Max_5m_Input]
    -> FootprintAreaCalculator [Clipper_Max_3m_Input]
    -> FootprintAreaCalculator [All_ListBasedFeatureMerger]
FootprintAreaCalculator
    IFC_UNIQUE_ID = @Value(ifc_unique_id)
    ELEVATION = @Value(Elevation)
    FloorIndex = 0
    IFC_PARENT_ID = @Value(ifc_parent_id)
    IFC_PARENT_UNIQUE_ID = @Value(ifc_parent_unique_id)
    FootprintArea -> FootprintAreaCalculator_FootprintArea
FootprintAreaCalculator_FootprintArea: Inspector

FME custom transformer FootprintAreaCalculator

Parameters:
- IFC_PARENT_UNIQUE_ID = @Value(ifc_parent_unique_id)   # Ifc Parent Unique Id
- IFC_UNIQUE_ID = @Value(ifc_unique_id)   # ifc_unique_id
- ELEVATION = @Value(Elevation)   # Elevation
- IFC_PARENT_ID = @Value(ifc_parent_id)   # Ifc Parent Id
- FloorIndex = 1   # First floor index

All_ListBasedFeatureMerger (input)
    -> ListBasedFeatureMerger [SUPPLIER]
IfSlab_Input (input)
    -> StoreyIndexFinder_2 [AttributeCreator_StoreyList_Input]
BuildingStorey_AggregatedList (input)
    -> StoreyIndexFinder_2 [PythonCaller_2_Input]
StoreyIndexFinder_2
    storeyIndex = $(FloorIndex)
    IFC_UNIQUE_ID = @Value(ifc_unique_id)
    Tester_StoreyIndex_Passed -> CreateBasisBYA [Input_storey]
    Tester_StoreyIndex_Passed -> StoreyIndexFinder_FirstFloor
StoreyIndexFinder_FirstFloor: Inspector
Note: Clip the building to be able to find the protruding parts.
Clipper_Max_3m_Input (input)
    -> Clipper_Max_3m_2
Clipper_Max_5m_Input (input)
    -> Clipper_Max_5m_3
Clipper_BottomEdge_Input (input)
    -> Clipper_BottomEdge_2
Note: Clip lowest part of the wall
Clipper_BottomEdge_2: Building_Clipper
    DISTANCE = 10
    OFFSET_Z = @Value(Elevation)
    IFC_PARENT_UNIQUE_ID = @Value(ifc_parent_unique_id)
    Output_extruded -> PointCloudClipper [Clipper]
    Output_clipper -> CreateBasisBYA [Input_facade]
    Rejected -> PointCloudClipper [Wall]
Note: Handle wall objects that won't clip with default FME Clipper
PointCloudClipper
    IFC_UNIQUE_ID = @Value(ifc_unique_id)
    IFC_PARENT_UNIQUE_ID = @Value(ifc_parent_unique_id)
    Output_2D -> CreateBasisBYA [Input_pointCloud]
CreateBasisBYA
    IFC_UNIQUE_ID = @Value(ifc_unique_id)
    -> AttributeManager_2
    -> Protruding_Part [Bufferer_Input]
    -> SurfaceFootprintReplacer_3
SurfaceFootprintReplacer_3
    SHADOW_MODE = Overhead Shadow
    OFFSET_Z = 0
    FOOTPRINT -> Snapper
Note: Calculate BUA, / scale from mm2 to m2
AreaCalculator
    AREA_TYPE = Plane Area
    MULT = 1/1000000
    AREA_ATTR = _area
    -> AttributeRounder
Note: Round to on dec.
AttributeRounder
    PLACES = 1
    ROUND_TYPE = Nearest
    SRC_ATTRS = _area
    -> AttributeKeeper_2
AttributeKeeper_2
    KEEP_ATTRS = _area
    -> FootprintArea (output)
FootprintArea (output)

Bookmark: Klipper byggnaden 0-3 m
Clipper_Max_3m_2: Building_Clipper
    DISTANCE = 3000
    OFFSET_Z = @Value(Elevation)
    IFC_PARENT_UNIQUE_ID = @Value(ifc_parent_unique_id)
    Output_extruded -> PointCloudClipper_5 [Clipper]
    Output_clipper -> Protruding_Part [Clipper_Byggnad]
    Rejected -> PointCloudClipper_5 [Wall]
PointCloudClipper_5
    IFC_UNIQUE_ID = @Value(ifc_unique_id)
    IFC_PARENT_UNIQUE_ID = @Value(ifc_parent_unique_id)
    Output_3D -> Protruding_Part [Clipper_Byggnad]

Bookmark: Klipper byggnaden 3-5 m
Clipper_Max_5m_3: Building_Clipper
    DISTANCE = 2000
    OFFSET_Z = @Value(Elevation)+3000
    IFC_PARENT_UNIQUE_ID = @Value(ifc_parent_unique_id)
    Output_extruded -> PointCloudClipper_6 [Clipper]
    Output_clipper -> Protruding_Part_2 [Clipper_Byggnad]
    Rejected -> PointCloudClipper_6 [Wall]
PointCloudClipper_6
    IFC_UNIQUE_ID = @Value(ifc_unique_id)
    IFC_PARENT_UNIQUE_ID = @Value(ifc_parent_unique_id)
    Output_3D -> Protruding_Part_2 [Clipper_Byggnad]

Bookmark: 0-3m, < 0,5m
Protruding_Part
    OFFSET = 500
    _ZMIN = @Value(_zmin)
    DISTANCE = 3000
    _ZMINVAL = @Value(_zminval)
    Output_Outside -> Aggregator

Bookmark: 3-5m, < 1,5m
Note: Flytta zmin +3000mm
AttributeManager_2
    ATTR_TABLE:
      SET_TO _zminval = @Value(_zminval)+3000
      SET_TO _zmin = +3000
    -> Protruding_Part_2 [Bufferer_Input]
Protruding_Part_2
    OFFSET = 1500
    _ZMIN = @Value(_zmin)
    DISTANCE = 2000
    _ZMINVAL = @Value(_zminval)
    Output_Outside -> Aggregator

Bookmark: Protruding parts
Note: Clip protruding parts (Output_Outside)
Aggregator
    LIST_NAME = ListName
    CONCAT_ATTRS = ifc_unique_id
    ORDERED = No
    MODE = Attributes Only
    SEP = ,
    LIST_ATTRS_TO_INCLUDE = ifc_unique_id
    ACCUM_ATTRS_NAME = Merge Incoming Attributes
    AGGREGATE -> ListElementCounter
ListElementCounter
    CNT_ATTR = nbrStoreys
    LIST_NAME = ListName{}
    -> ListBasedFeatureMerger [REQUESTOR]
Note: Retrive the whole protruding object with ifc_unique_id, project and merge with "BasisBUA"
ListBasedFeatureMerger
    REFEEATTR = @Value(ifc_unique_id)
    MODE = AUTO
    MERGE_TYPE = Geometry
    BUILD_INCOMPLETE = Merge Supplier Information
    REFERATTR = ListName{}.ifc_unique_id
    PROCESS_DUPS = Yes
    GEOM_TYPE = Build Aggregates
    MERGED -> SurfaceFootprintReplacer_2
SurfaceFootprintReplacer_2
    SHADOW_MODE = Overhead Shadow
    OFFSET_Z = 0
    FOOTPRINT -> Snapper
Dissolver_2
    DEAGGREGATE_INPUT = Yes
    CONNECT_Z_MODE = First Wins
    NO_OVRLP = No
    ACCUM_INPUT_ATTRS = Use Attributes From One Feature
    AREA -> AreaCalculator

Bookmark: Prepare for dissolve
  Snapp areas that won't dissolve (because they don't intersect/ are connected)
Snapper
    CLEANING_TOLERANCE_MODE = AUTO
    TOLERANCE = 10
    SNAPTYPE_PARAM = Segment Snapping
    SNAPPED -> Dissolver_2
    UNTOUCHED -> Dissolver_2

FME custom transformer PointCloudClipper

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    GROUP_BY = ifc_unique_id
    EXTRACT_RASTER_NODATA_NAME = No
    SPACING = 20
    ATTRS_TO_PRESERVE = ifc_parent_unique_id,String
    ACCUM_ATTRS_NAME = Yes
    -> Clipper_2 [CLIPPEE]
Clipper (input)
    -> Clipper_2 [CLIPPER]
Clipper_2
    CREATE_AGGREGATES = Yes
    MEASURE_TYPE = Continuous
    LINES_AS_SEGMENTS = No
    CLIPPED_ATTR = _clipped
    PRESERVE_CLIPPEE_EXTENTS = No
    VAL_SOURCE = Clippee Only
    MISSING_VAL_MODE = Compute
    BOUNDARY_CASES = Treat as Inside
    CLIP_TYPE = Single Clipper
    INSIDE -> PointCloudCoercer
    INSIDE -> Output_3D (output)
PointCloudCoercer
    POINT_COMPONENTS_PRESERVE_DISPLAY = Attributes
    PART_NUMBER_ATTR_NAME = _part_number
    CONVERT_TO_DISPLAY = Individual Points
    ACCUM_ATTRS_NAME = Yes
    COERCED -> 2DForcer
2DForcer
    2D -> HullAccumulator
HullAccumulator
    GROUP_BY = ifc_unique_id
    HULLTYPE_PARAM = Convex ()
    3DMODE_PARAM = 2D
    HULL -> Output_2D (output)
Output_2D (output)
Output_3D (output)

FME custom transformer MinZ

Input (input)
    -> AttributeCreator
AttributeCreator
    ATTR_TABLE = SET_TO _zminval
    -> BoundsExtractor
BoundsExtractor
    YMIN = _ymin
    ZMIN = _zmin
    XMAX = _xmax
    XMIN = _xmin
    YMAX = _ymax
    ZMAX = _zmax
    -> PythonCaller
PythonCaller
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    PYTHONSYMBOL = FeatureProcessor
    -> Output (output)
Output (output)

FME custom transformer Protruding_Part

Parameters:
- _ZMINVAL = @Value(_zminval)   # Zminval
- OFFSET = 500   # Buffer Amount
- DISTANCE = 3000   # Distance
- _ZMIN = @Value(_zmin)   # Zmin

Bufferer_Input (input)
    -> Bufferer
Clipper_Byggnad (input)
    -> Clipper [CLIPPEE]
Clipper
    CREATE_AGGREGATES = Yes
    MEASURE_TYPE = Continuous
    ATTR_ACCUM_MODE = Merge Clipper
    LINES_AS_SEGMENTS = No
    CLIPPED_ATTR = _clipped
    CONNECT_Z_MODE = First Wins
    PRESERVE_CLIPPEE_EXTENTS = No
    ATTR_CONFLICT_RES = Use Clippee
    VAL_SOURCE = Clippee Only
    MISSING_VAL_MODE = Compute
    BOUNDARY_CASES = Treat as Inside
    CLIP_TYPE = Multiple Clippers
    DEFAULT_VAL = 0
    INSIDE -> Output_Inside (output)
    OUTSIDE -> GeometryValidator
    <REJECTED> -> Clipper__Rejected_
Output_Inside (output)
Note: Kontrollera så att objekten har geometri
GeometryValidator
    CONNECT_Z_MODE_TR = First Wins
    NAN_REMOVAL = NAN_REMOVAL
    SUMMARY = Detailed
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    AREA_ORIENTATION = AREA_ORIENTATION
    REPAIR = Yes
    PRESETS = Basic Geometry Integrity
    ISSUE_ATTR_NAME = _issues
    ORIENTATION_CHECK_DIR = Valid
    TYPE_REPAIR = TYPE_REPAIR
    ARC_ENDPOINT_TOLERANCE_MODE = Auto
    NULL_REMOVAL = NULL_REMOVAL
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    CORNER_STYLE = Round
    OFFSET = $(OFFSET)
    ANGLE = 1
    CAP_STYLE = Round
    BUFFERED -> SurfaceFootprintReplacer
    BUFFERED -> Bufferer_Buffered
Bufferer_Buffered: Inspector [off]
SurfaceFootprintReplacer
    SHADOW_MODE = Overhead Shadow
    OFFSET_Z = @Value(_zminval)
    FOOTPRINT -> Extruder
Note: Extrude 3 el 2 m
Extruder
    DIRECTION = Auto
    DISTANCE = $(DISTANCE)
    EXTRUDED -> Clipper [CLIPPER]
    EXTRUDED -> Extruder_Extruded
    <REJECTED> -> Extruder__Rejected_
Extruder_Extruded: Inspector
Extruder__Rejected_: Inspector

FME custom transformer StoreyIndexFinder

Parameters:
- storeyIndex = 1   # Floor index
- IFC_UNIQUE_ID = @Value(ifc_unique_id)   # Ifc Unique Id

Note: Connect to UUID creator for the walls
AttributeCreator_StoreyList_Input (input)
    -> AttributeCreator_StoreyList
AttributeCreator_StoreyList
    ATTR_TABLE = SET_TO storeyListIndex
    -> PythonCaller_2
Note: Connect to ListElementCounter / belonging to IfcBuildingStorey
PythonCaller_2_Input (input)
    -> Aggregator_2
Aggregator_2
    LIST_NAME = buildingStoreysID
    CONCAT_ATTRS = ifc_unique_id
    ORDERED = No
    MODE = Attributes Only
    SEP = ,
    LIST_ATTRS_TO_INCLUDE = ifc_unique_id
    ACCUM_ATTRS_NAME = Merge Incoming Attributes
    AGGREGATE -> ListElementCounter
ListElementCounter
    CNT_ATTR = nbrStoreys
    LIST_NAME = buildingStoreysID{}
    -> PythonCaller_2
PythonCaller_2
    PYTHONSOURCE:
      import fme
      import fmeobjects
      # Template Function interface:
      # When using this function, make sure its name is set as the value of
      # the 'Class or Function to Process Features' transformer parameter
      def processFeature(feature):
          pass


      def listFinder(f): # f - the list with all features
          pos = 0 # Index in list
          while pos < len(f):
              attList = f[pos].getAllAttributeNames() # get all feature attributes
              for att in attList:
                  if 'buildingStoreysID' in att:
                      return f[pos].getAttribute('buildingStoreysID{}.ifc_unique_id')
              pos += 1
          return None

      def storeyIndexFinder(fe,storeyList):
          # Returns the index in the storey list of current feature
          parentID = fe.getAttribute('ifc_parent_unique_id')
          pos = 0
          while pos < len(storeyList):
              if storeyList[pos] == parentID:
                  return pos
              else:
                  pass # Do nothing
              pos += 1

      # Template Class Interface:
      # When using this class, make sure its name is set as the value of
      # the 'Class or Function to Process Features' transformer parameter
      class FeatureProcessor(object):
          def __init__(self):
              self.featureList = []
              self.logger = fmeobjects.FMELogFile()
              # logger.logMessageString('message')

          def input(self,feature): # This function is called every time a feature is added
              self.featureList.append(feature)

          def close(self):
              li = listFinder(self.featureList) # Return a list with storey id
              for f in self.featureList:
                  currIndex = storeyIndexFinder(f, li) # Check feature parent_id against list with storey id
                  f.setAttribute("storeyListIndex", currIndex)
                  self.pyoutput(f)
    NEW_ATTRIBUTES = storeyListIndex
    PYTHONSYMBOL = FeatureProcessor
    -> Tester_StoreyIndex
Note: Which storey index to include
Tester_StoreyIndex
    TEST_MODE = Automatic
    BOOL_OP = OR
    TEST_DESCRIPTION = ""
    TEST_CLAUSE = TEST @Value(storeyListIndex) = $(storeyIndex)
    PASSED -> Tester_StoreyIndex_Passed (output)
Tester_StoreyIndex_Passed (output)

FME custom transformer CreateBasisBYA

Parameters:
- IFC_UNIQUE_ID = @Value(ifc_unique_id)   # Ifc Unique Id

Bookmark: BasisBYA
Input_storey (input)
    -> MinZ_2
MinZ_2
    -> SurfaceFootprintReplacer_3
SurfaceFootprintReplacer_3
    SHADOW_MODE = Overhead Shadow
    OFFSET_Z = @Value(_zminval)
    FOOTPRINT -> Snapper
Input_pointCloud (input)
    -> MinZ
Input_facade (input)
    -> MinZ
MinZ
    -> SurfaceFootprintReplacer_2
SurfaceFootprintReplacer_2
    SHADOW_MODE = Overhead Shadow
    OFFSET_Z = @Value(_zminval)
    FOOTPRINT -> HullAccumulator
    <REJECTED> -> SurfaceFootprintReplacer_2__Rejected_
HullAccumulator
    GROUP_BY = ifc_unique_id _zminval
    HULLTYPE_PARAM = Convex ()
    DEFAULTZ = @Value(_zminval)
    3DMODE_PARAM = 3D
    HULL -> Snapper
Dissolver_2
    DEAGGREGATE_INPUT = Yes
    CONNECT_Z_MODE = Extend
    NO_OVRLP = No
    ACCUM_INPUT_ATTRS = Merge Incoming Attributes
    AREA -> BoundsExtractor
BoundsExtractor
    YMIN = _ymin
    ZMIN = _zmin
    XMAX = _xmax
    XMIN = _xmin
    YMAX = _ymax
    ZMAX = _zmax
    -> SurfaceFootprintReplacer
SurfaceFootprintReplacer
    SHADOW_MODE = Overhead Shadow
    OFFSET_Z = @Value(_zminval)
    FOOTPRINT -> DonutHoleExtractor_2
DonutHoleExtractor_2
    DEAGGREGATE_INPUT = Yes
    OUTERSHELL -> Output (output)
Output (output)
SurfaceFootprintReplacer_2__Rejected_: Inspector [off]

Bookmark: Prepare for dissolve
  Snapp areas that won't dissolve (because they don't intersect/ are connected)
Snapper
    CLEANING_TOLERANCE_MODE = AUTO
    TOLERANCE = 10
    SNAPTYPE_PARAM = Segment Snapping
    SNAPPED -> Dissolver_2
    UNTOUCHED -> Dissolver_2

FME custom transformer Building_Clipper

Parameters:
- IFC_PARENT_UNIQUE_ID = @Value(ifc_parent_unique_id)   # Ifc Parent Unique Id
- DISTANCE = 10   # Distance
- OFFSET_Z = 0   # Z" Elevation

Input (input)
    -> Deaggregator
    -> BoundsExtractor
    -> BoundingBoxAccumulator
    -> Input
BoundingBoxAccumulator
    ATTR_NAME = _topferIndex
    DESTINATION_SCALE = 1
    TOPFER_INDEX = No
    SOURCE_SCALE = 1
    ACCUM_ATTRS_NAME = Use Attributes From One Feature
    BOUNDING_BOX -> FeatureMerger [REQUESTOR]
BoundsExtractor
    YMIN = _ymin
    ZMIN = _zmin
    XMAX = _xmax
    XMIN = _xmin
    YMAX = _ymax
    ZMAX = _zmax
    -> ListBuilder
ListBuilder
    GROUPS_ORDERED = No
    LIST_ATTRS_TO_INCLUDE = _zmin ifc_parent_unique_id
    LIST_NAME = _list
    -> ListRangeExtractor
ListRangeExtractor
    MIN = _min
    SRC_LIST = _list{}._zmin
    MAX = _max
    -> FeatureMerger [SUPPLIER]
FeatureMerger
    IGNORE_NULLS = No
    REJECT_NULL_MISSING_KEYS = No
    JOIN_KEYS = @Value(ifc_parent_unique_id) @Value(_list{0}.ifc_parent_unique_id) AUTO
    MERGE_TYPE = Attributes Only
    ATTR_ACCUM_MODE = Merge Supplier
    SUPPLIERS_FIRST = No
    PROCESS_DUPS = No
    ATTR_CONFLICT_RES = Use Requestor
    MERGED -> SurfaceFootprintReplacer
SurfaceFootprintReplacer
    SHADOW_MODE = Overhead Shadow
    OFFSET_Z = $(OFFSET_Z)+@Value(_min)
    FOOTPRINT -> Extruder
Extruder
    DIRECTION = Vertical
    DISTANCE = $(DISTANCE)
    EXTRUDED -> Clipper_2 [CLIPPER]
    EXTRUDED -> Output_extruded (output)
Output_extruded (output)
Deaggregator
    EXPLODE_INSTANCES = No
    ID_ATTR = _hierarchy_id
    COPY_ATTR = Every Node
    GEOM_NAME_FIELD = _geometry_name
    PART_NUMBER_FIELD = _part_number
    MODE = Flatten One Level
    CHILD_ID_ATTR = _hierarchy_child_id_list
    LIST_ATTR_MODE_LOOKUP = LEAN
    ID_SELECTION = ID and Parent ID
    SPLIT_COMPOSITES = No
    PARENT_ID_ATTR = _hierarchy_parent_id
    DEAGGREGATED -> GeometryFilter
GeometryFilter
    BREAK_AGG = No
    GEOM_PORT_NAMES = Solid
    SOLID -> Clipper_2 [CLIPPEE]
Clipper_2
    CREATE_AGGREGATES = Yes
    MEASURE_TYPE = Continuous
    LINES_AS_SEGMENTS = No
    CLIPPED_ATTR = _clipped
    PRESERVE_CLIPPEE_EXTENTS = No
    VAL_SOURCE = Clippee Only
    MISSING_VAL_MODE = Compute
    BOUNDARY_CASES = Treat as Inside
    CLIP_TYPE = Multiple Clippers
    INSIDE -> Output_clipper (output)
    <REJECTED> -> Rejected (output)
Output_clipper (output)
Rejected (output)
Input: Inspector [off]
