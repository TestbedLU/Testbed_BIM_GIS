FME workspace Hjaltevadshus Spira 175 - without object for BUA.fmwt
Title: Hjaltevadshus Spira 175 - without object for BUA

Parameters:
- SourceDataset_IFC_5 = $(FME_MF_DIR)1/175/Spira 175 - Spv  - IFC.ifc   # Source Industry Foundation Class (IFC) File(s)

Readers:
- IFC_1: IFC from $(SourceDataset_IFC_5) in XY-MM

Bookmark: Spira 175
IfcSlab (reader IFC_1)
    attributes: GlobalId char(22), Name string, Description string, ObjectType string, Tag string, PredefinedType enumeration, Axis geometry, Body geometry, Box geometry, FootPrint geometry
    -> IfcSlab_-__FootprintAreaCalculator_All_ListBasedFeatureMerger
IfcSlab_-__FootprintAreaCalculator_All_ListBasedFeatureMerger: Junction
    -> FootprintAreaCalculator [All_ListBasedFeatureMerger]
    -> FootprintAreaCalculator [IfSlab_Input]
    -> FootprintAreaCalculator [Clipper_Max_3m_Input]
    -> FootprintAreaCalculator [Clipper_Max_5m_Input]
IfcBuildingStorey (reader IFC_1)
    attributes: GlobalId char(22), Name string, Description string, ObjectType string, LongName string, CompositionType enumeration, Elevation real, Axis geometry, Body geometry, Box geometry, FootPrint geometry
    -> FootprintAreaCalculator [BuildingStorey_AggregatedList]
IfcWall (reader IFC_1)
    attributes: GlobalId char(22), Name string, Description string, ObjectType string, Tag string, Axis geometry, Body geometry, Box geometry, FootPrint geometry
    -> Tester
IfcWallStandardCase (reader IFC_1)
    attributes: GlobalId char(22), Name string, Description string, ObjectType string, Tag string, Axis geometry, Body geometry, Box geometry, FootPrint geometry
    -> Tester
Note: Remove a wall under the house
Tester
    BOOL_OP = OR
    TEST_MODE = Automatic
    TEST_DESCRIPTION = ""
    TEST_CLAUSE = TEST @Value(ifc_unique_id) != 1w4KozkgnE5h9WFsZPGqIX_91216
    PASSED -> FootprintAreaCalculator [Clipper_BottomEdge_Input]
    PASSED -> FootprintAreaCalculator [Clipper_Max_5m_Input]
    PASSED -> FootprintAreaCalculator [Clipper_Max_3m_Input]
    PASSED -> FootprintAreaCalculator [All_ListBasedFeatureMerger]
IfcRoof (reader IFC_1)
    attributes: GlobalId char(22), Name string, Description string, ObjectType string, Tag string, ShapeType enumeration, Axis geometry, Body geometry, Box geometry, FootPrint geometry
    -> IfcRoof_-__FootprintAreaCalculator_All_ListBasedFeatureMerger
IfcRoof_-__FootprintAreaCalculator_All_ListBasedFeatureMerger: Junction
    -> FootprintAreaCalculator [Clipper_Max_5m_Input]
    -> FootprintAreaCalculator [Clipper_Max_3m_Input]
    -> FootprintAreaCalculator [All_ListBasedFeatureMerger]
FootprintAreaCalculator
    ELEVATION = @Value(Elevation)
    FloorIndex = 1
    IFC_UNIQUE_ID = @Value(ifc_unique_id)
    IFC_PARENT_ID = @Value(ifc_parent_id)
    IFC_PARENT_UNIQUE_ID = @Value(ifc_parent_unique_id)
    FootprintArea -> Extruder_2
    FootprintArea -> FootprintAreaCalculator_FootprintArea
FootprintAreaCalculator_FootprintArea: Inspector

Bookmark: -> GML
Note: Temp 5m, alt senare beräknad höjd / för byggnaden
Extruder_2 [off]
    DIRECTION = Auto
    DISTANCE = 5000
    EXTRUDED -> Extruder_Extruded_2 [off]
    EXTRUDED -> SolidBuilder_2 [off]
Extruder_Extruded_2: Inspector [off]
SolidBuilder_2 [off]
    GROUP_BY = _area
    DROP_HOLES = No
    HOLE_ATTR = _is_void
    SOLID -> SolidBuilder_Solid_2 [off]
    SOLID -> CsmapReprojector_3 [off]
SolidBuilder_Solid_2: Inspector [off]
CsmapReprojector_3 [off]
    VERTICAL_HANDLING = Heights are relative to the ellipsoid(s) or geocentric
    INTERPOLATION_TYPE_NAME = Nearest Neighbor
    SOURCE = XY-MM
    DEST = SWEREF-99-18-00
    RASTER_CELL_SIZE = Preserve Cells
    REPROJECTED -> AttributeCreator_3 [off]
AttributeCreator_3 [off]
    ATTR_TABLE = SET_TO BYA_area = @Value(_area)

FME custom transformer PointCloudClipper

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    GROUP_BY = ifc_unique_id
    ATTRS_TO_PRESERVE = ifc_parent_unique_id,String
    EXTRACT_RASTER_NODATA_NAME = No
    SPACING = 20
    ACCUM_ATTRS_NAME = Yes
    -> Clipper_2 [CLIPPEE]
Clipper (input)
    -> Clipper_2 [CLIPPER]
Clipper_2
    CLIPPED_ATTR = _clipped
    PRESERVE_CLIPPEE_EXTENTS = No
    CREATE_AGGREGATES = Yes
    LINES_AS_SEGMENTS = No
    BOUNDARY_CASES = Treat as Inside
    CLIP_TYPE = Single Clipper
    MISSING_VAL_MODE = Compute
    VAL_SOURCE = Clippee Only
    MEASURE_TYPE = Continuous
    INSIDE -> PointCloudCoercer
    INSIDE -> Output_3D (output)
PointCloudCoercer
    CONVERT_TO_DISPLAY = Individual Points
    POINT_COMPONENTS_PRESERVE_DISPLAY = Attributes
    ACCUM_ATTRS_NAME = Yes
    PART_NUMBER_ATTR_NAME = _part_number
    COERCED -> 2DForcer
2DForcer
    2D -> HullAccumulator
HullAccumulator
    GROUP_BY = ifc_unique_id
    HULLTYPE_PARAM = Convex ()
    3DMODE_PARAM = 2D
    HULL -> Output_2D (output)
Output_2D (output)
Output_3D (output)

FME custom transformer Building_Clipper

Parameters:
- IFC_PARENT_UNIQUE_ID = @Value(ifc_parent_unique_id)   # Ifc Parent Unique Id
- DISTANCE = 10   # Distance
- OFFSET_Z = 0   # Z" Elevation

Input (input)
    -> Deaggregator
    -> BoundsExtractor
    -> BoundingBoxAccumulator
    -> Input
BoundingBoxAccumulator
    ATTR_NAME = _topferIndex
    DESTINATION_SCALE = 1
    TOPFER_INDEX = No
    SOURCE_SCALE = 1
    ACCUM_ATTRS_NAME = Use Attributes From One Feature
    BOUNDING_BOX -> FeatureMerger [REQUESTOR]
BoundsExtractor
    YMAX = _ymax
    YMIN = _ymin
    ZMAX = _zmax
    XMIN = _xmin
    ZMIN = _zmin
    XMAX = _xmax
    -> ListBuilder
ListBuilder
    LIST_ATTRS_TO_INCLUDE = _zmin ifc_parent_unique_id
    LIST_NAME = _list
    GROUPS_ORDERED = No
    -> ListRangeExtractor
ListRangeExtractor
    MIN = _min
    SRC_LIST = _list{}._zmin
    MAX = _max
    -> FeatureMerger [SUPPLIER]
FeatureMerger
    ATTR_CONFLICT_RES = Use Requestor
    ATTR_ACCUM_MODE = Merge Supplier
    PROCESS_DUPS = No
    SUPPLIERS_FIRST = No
    IGNORE_NULLS = No
    REJECT_NULL_MISSING_KEYS = No
    MERGE_TYPE = Attributes Only
    JOIN_KEYS = @Value(ifc_parent_unique_id) @Value(_list{0}.ifc_parent_unique_id) AUTO
    MERGED -> SurfaceFootprintReplacer
SurfaceFootprintReplacer
    SHADOW_MODE = Overhead Shadow
    OFFSET_Z = $(OFFSET_Z)+@Value(_min)
    FOOTPRINT -> Extruder
Extruder
    DIRECTION = Vertical
    DISTANCE = $(DISTANCE)
    EXTRUDED -> Clipper_2 [CLIPPER]
    EXTRUDED -> Output_extruded (output)
Output_extruded (output)
Deaggregator
    EXPLODE_INSTANCES = No
    CHILD_ID_ATTR = _hierarchy_child_id_list
    PART_NUMBER_FIELD = _part_number
    ID_ATTR = _hierarchy_id
    MODE = Flatten One Level
    COPY_ATTR = Every Node
    PARENT_ID_ATTR = _hierarchy_parent_id
    ID_SELECTION = ID and Parent ID
    SPLIT_COMPOSITES = No
    LIST_ATTR_MODE_LOOKUP = LEAN
    GEOM_NAME_FIELD = _geometry_name
    DEAGGREGATED -> GeometryFilter
GeometryFilter
    BREAK_AGG = No
    GEOM_PORT_NAMES = Solid
    SOLID -> Clipper_2 [CLIPPEE]
Clipper_2
    CLIPPED_ATTR = _clipped
    PRESERVE_CLIPPEE_EXTENTS = No
    CREATE_AGGREGATES = Yes
    LINES_AS_SEGMENTS = No
    BOUNDARY_CASES = Treat as Inside
    CLIP_TYPE = Multiple Clippers
    MISSING_VAL_MODE = Compute
    VAL_SOURCE = Clippee Only
    MEASURE_TYPE = Continuous
    INSIDE -> Output_clipper (output)
    <REJECTED> -> Rejected (output)
Output_clipper (output)
Rejected (output)
Input: Inspector [off]

FME custom transformer CreateBasisBYA_2

Parameters:
- IFC_UNIQUE_ID = @Value(ifc_unique_id)   # Ifc Unique Id

Bookmark: BasisBYA
Input_storey (input)
    -> MinZ_2
MinZ_2
    -> SurfaceFootprintReplacer_3
SurfaceFootprintReplacer_3
    SHADOW_MODE = Overhead Shadow
    OFFSET_Z = @Value(_zminval)
    FOOTPRINT -> Dissolver_2
Input_pointCloud (input)
    -> MinZ
Input_facade (input)
    -> MinZ
MinZ
    -> SurfaceFootprintReplacer_2
SurfaceFootprintReplacer_2
    SHADOW_MODE = Overhead Shadow
    OFFSET_Z = @Value(_zminval)
    FOOTPRINT -> HullAccumulator
    <REJECTED> -> SurfaceFootprintReplacer_2__Rejected_
HullAccumulator
    GROUP_BY = ifc_unique_id _zminval
    HULLTYPE_PARAM = Convex ()
    3DMODE_PARAM = 3D
    DEFAULTZ = @Value(_zminval)
    HULL -> Dissolver_2
Dissolver_2
    DEAGGREGATE_INPUT = Yes
    NO_OVRLP = No
    CONNECT_Z_MODE = Extend
    ACCUM_INPUT_ATTRS = Merge Incoming Attributes
    AREA -> BoundsExtractor
BoundsExtractor
    YMAX = _ymax
    YMIN = _ymin
    ZMAX = _zmax
    XMIN = _xmin
    ZMIN = _zmin
    XMAX = _xmax
    -> SurfaceFootprintReplacer
SurfaceFootprintReplacer
    SHADOW_MODE = Overhead Shadow
    OFFSET_Z = @Value(_zmin)
    FOOTPRINT -> DonutHoleExtractor_2
DonutHoleExtractor_2
    DEAGGREGATE_INPUT = Yes
    OUTERSHELL -> Output (output)
Output (output)
SurfaceFootprintReplacer_2__Rejected_: Inspector [off]

Bookmark: Test1
Dissolver [off]
    DEAGGREGATE_INPUT = Yes
    NO_OVRLP = No
    CONNECT_Z_MODE = First Wins
    ACCUM_INPUT_ATTRS = Use Attributes From One Feature
    AREA -> DonutHoleExtractor [off]
    AREA -> Dissolver_Area [off]
    INTERIOR_LINE -> Dissolver_InteriorLine [off]
    <REJECTED> -> Dissolver__Rejected_ [off]
Dissolver_Area: Inspector [off]
DonutHoleExtractor [off]
    DEAGGREGATE_INPUT = Yes
    OUTERSHELL -> Aggregator [off]
Aggregator [off]
    SEP = ,
    MODE = Geometry - Assemble One Level
    ACCUM_ATTRS_NAME = Use Attributes From One Feature
    ORDERED = No
    AGGREGATE_TYPE = Homogeneous Collection (If Possible)
    AGGREGATE -> Aggregator_Aggregate [off]
Aggregator_Aggregate: Inspector [off]
Dissolver_InteriorLine: Inspector [off]
Dissolver__Rejected_: Inspector [off]

Bookmark: Test2
GeometryCoercer [off]
    GQUERY:
      for $geom in //geometry
      where $geom/count(parent::geometry) = 0
      return number($geom/@fme_id)
    KIND = fme_line
    COERCED -> Snapper_2 [off]
    UNTOUCHED -> Snapper_2 [off]
Snapper_2 [off]
    SAVE_SHORT_LINES = No
    TOLERANCE = 10
    SNAPTYPE_PARAM = End Point Snapping
    EXTEND_LINES = NEVER
    SNAPPED -> AreaBuilder [off]
    SNAPPED -> Snapper_2_Snapped [off]
    UNTOUCHED -> AreaBuilder [off]
    UNTOUCHED -> Snapper_2_Untouched [off]
AreaBuilder [off]
    DONUT_CREATION = Yes
    ALLOW_CYCLES = No
    SNAPTYPE_PARAM = None
    LINES_AS_SEGMENTS = No
    CHECK_CURVE_DIRECTION = No
    SNAP_TOLERANCE = 0
    CONSIDER_NODE_ELEVATION = no
    CONNECT_Z_MODE = First Wins
    DROP_HOLES = No
    POLY_ACCUM_ATTRS_NAME = Use Attributes From One Feature
    POLY_LIST_ATTRS_TO_INCLUDE_MODE = Selected Attributes
    AREA -> AreaAmalgamator [AREAS] [off]
    AREA -> AreaBuilder_Area [off]
AreaAmalgamator [off]
    AMALG_MODE = Binary Amalgamation
    MAX_TRIANGLE_LENGTH = 10
    MAX_TRIANGLE_WIDTH = 10
    MIN_HOLE_AREA = 100
    DISSOLVE_INPUT = Yes
    AMALGAMATED -> AreaAmalgamator_Amalgamated [off]
AreaAmalgamator_Amalgamated: Inspector [off]
AreaBuilder_Area: Inspector [off]
Snapper_2_Snapped: Inspector [off]
Snapper_2_Untouched: Inspector [off]
AreaOnAreaOverlayer [off]
    DEAGGREGATE_INPUT = Yes
    OVC_ATTR = _overlaps
    CONNECT_Z_MODE = First Wins
    ACCUM_ATTRS_NAME = Use Attributes From One Feature
    AREA -> AreaOnAreaOverlayer_Area [off]
    <REJECTED> -> AreaOnAreaOverlayer__Rejected_ [off]
AreaOnAreaOverlayer_Area: Inspector [off]
AreaOnAreaOverlayer__Rejected_: Inspector [off]

FME custom transformer PointCloudClipper_2

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    GROUP_BY = ifc_unique_id
    ATTRS_TO_PRESERVE = ifc_parent_unique_id,String
    EXTRACT_RASTER_NODATA_NAME = No
    SPACING = 20
    ACCUM_ATTRS_NAME = Yes
    -> Clipper_2 [CLIPPEE]
Clipper (input)
    -> Clipper_2 [CLIPPER]
Clipper_2
    CLIPPED_ATTR = _clipped
    PRESERVE_CLIPPEE_EXTENTS = No
    CREATE_AGGREGATES = Yes
    LINES_AS_SEGMENTS = No
    BOUNDARY_CASES = Treat as Inside
    CLIP_TYPE = Single Clipper
    MISSING_VAL_MODE = Compute
    VAL_SOURCE = Clippee Only
    MEASURE_TYPE = Continuous
    INSIDE -> PointCloudCoercer
    INSIDE -> Output_3D (output)
PointCloudCoercer
    CONVERT_TO_DISPLAY = Individual Points
    POINT_COMPONENTS_PRESERVE_DISPLAY = Attributes
    ACCUM_ATTRS_NAME = Yes
    PART_NUMBER_ATTR_NAME = _part_number
    COERCED -> 2DForcer
2DForcer
    2D -> HullAccumulator
HullAccumulator
    GROUP_BY = ifc_unique_id
    HULLTYPE_PARAM = Convex ()
    3DMODE_PARAM = 2D
    HULL -> Output_2D (output)
Output_2D (output)
Output_3D (output)

FME custom transformer MinZ

Input (input)
    -> AttributeCreator
AttributeCreator
    ATTR_TABLE = SET_TO _zminval
    -> BoundsExtractor
BoundsExtractor
    YMAX = _ymax
    YMIN = _ymin
    ZMAX = _zmax
    XMIN = _xmin
    ZMIN = _zmin
    XMAX = _xmax
    -> PythonCaller
PythonCaller
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    PYTHONSYMBOL = FeatureProcessor
    -> Output (output)
Output (output)

FME custom transformer Protruding_Part_2

Parameters:
- _ZMINVAL = @Value(_zminval)   # Zminval
- OFFSET = 500   # Buffer Amount
- DISTANCE = 3000   # Distance
- _ZMIN = @Value(_zmin)   # Zmin

Bufferer_Input (input)
    -> Bufferer
Clipper_Byggnad (input)
    -> Clipper [CLIPPEE]
Clipper
    CLIPPED_ATTR = _clipped
    ATTR_CONFLICT_RES = Use Clippee
    PRESERVE_CLIPPEE_EXTENTS = No
    ATTR_ACCUM_MODE = Merge Clipper
    CREATE_AGGREGATES = Yes
    LINES_AS_SEGMENTS = No
    BOUNDARY_CASES = Treat as Inside
    CONNECT_Z_MODE = First Wins
    CLIP_TYPE = Multiple Clippers
    MISSING_VAL_MODE = Compute
    VAL_SOURCE = Clippee Only
    MEASURE_TYPE = Continuous
    DEFAULT_VAL = 0
    INSIDE -> Output_Inside (output)
    OUTSIDE -> GeometryValidator
    <REJECTED> -> Clipper__Rejected_
Output_Inside (output)
Note: Kontrollera så att objekten har geometri
GeometryValidator
    CONNECT_Z_MODE_TR = First Wins
    ISSUE_ATTR_NAME = _issues
    TYPE_REPAIR = TYPE_REPAIR
    AREA_ORIENTATION = AREA_ORIENTATION
    PRESETS = Basic Geometry Integrity
    SUMMARY = Detailed
    REPAIR = Yes
    NULL_REMOVAL = NULL_REMOVAL
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    ARC_ENDPOINT_TOLERANCE_MODE = Auto
    ORIENTATION_CHECK_DIR = Valid
    NAN_REMOVAL = NAN_REMOVAL
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    CORNER_STYLE = Round
    ANGLE = 1
    CAP_STYLE = Round
    OFFSET = $(OFFSET)
    BUFFERED -> SurfaceFootprintReplacer
    BUFFERED -> Bufferer_Buffered
Bufferer_Buffered: Inspector [off]
SurfaceFootprintReplacer
    SHADOW_MODE = Overhead Shadow
    OFFSET_Z = @Value(_zmin)
    FOOTPRINT -> Extruder
Note: Extrude 3 el 2 m
Extruder
    DIRECTION = Auto
    DISTANCE = $(DISTANCE)
    EXTRUDED -> Extruder_Extruded
    EXTRUDED -> Clipper [CLIPPER]
    <REJECTED> -> Extruder__Rejected_
Extruder_Extruded: Inspector
Extruder__Rejected_: Inspector

FME custom transformer StoreyIndexFinder

Parameters:
- storeyIndex = 1   # Floor index
- IFC_UNIQUE_ID = @Value(ifc_unique_id)   # Ifc Unique Id

Note: Connect to UUID creator for the walls
AttributeCreator_StoreyList_Input (input)
    -> AttributeCreator_StoreyList
AttributeCreator_StoreyList
    ATTR_TABLE = SET_TO storeyListIndex
    -> PythonCaller_2
Note: Connect to ListElementCounter / belonging to IfcBuildingStorey
PythonCaller_2_Input (input)
    -> Aggregator_2
Aggregator_2
    SEP = ,
    MODE = Attributes Only
    LIST_ATTRS_TO_INCLUDE = ifc_unique_id
    LIST_NAME = buildingStoreysID
    CONCAT_ATTRS = ifc_unique_id
    ACCUM_ATTRS_NAME = Merge Incoming Attributes
    ORDERED = No
    AGGREGATE -> ListElementCounter
ListElementCounter
    LIST_NAME = buildingStoreysID{}
    CNT_ATTR = nbrStoreys
    -> PythonCaller_2
PythonCaller_2
    NEW_ATTRIBUTES = storeyListIndex
    PYTHONSOURCE:
      import fme
      import fmeobjects
      # Template Function interface:
      # When using this function, make sure its name is set as the value of
      # the 'Class or Function to Process Features' transformer parameter
      def processFeature(feature):
          pass


      def listFinder(f): # f - the list with all features
          pos = 0 # Index in list
          while pos < len(f):
              attList = f[pos].getAllAttributeNames() # get all feature attributes
              for att in attList:
                  if 'buildingStoreysID' in att:
                      return f[pos].getAttribute('buildingStoreysID{}.ifc_unique_id')
              pos += 1
          return None

      def storeyIndexFinder(fe,storeyList):
          # Returns the index in the storey list of current feature
          parentID = fe.getAttribute('ifc_parent_unique_id')
          pos = 0
          while pos < len(storeyList):
              if storeyList[pos] == parentID:
                  return pos
              else:
                  pass # Do nothing
              pos += 1

      # Template Class Interface:
      # When using this class, make sure its name is set as the value of
      # the 'Class or Function to Process Features' transformer parameter
      class FeatureProcessor(object):
          def __init__(self):
              self.featureList = []
              self.logger = fmeobjects.FMELogFile()
              # logger.logMessageString('message')

          def input(self,feature): # This function is called every time a feature is added
              self.featureList.append(feature)

          def close(self):
              li = listFinder(self.featureList) # Return a list with storey id
              for f in self.featureList:
                  currIndex = storeyIndexFinder(f, li) # Check feature parent_id against list with storey id
                  f.setAttribute("storeyListIndex", currIndex)
                  self.pyoutput(f)
    PYTHONSYMBOL = FeatureProcessor
    -> Tester_StoreyIndex
Note: Which storey index to include
Tester_StoreyIndex
    BOOL_OP = OR
    TEST_MODE = Automatic
    TEST_DESCRIPTION = ""
    TEST_CLAUSE = TEST @Value(storeyListIndex) = $(storeyIndex)
    PASSED -> Tester_StoreyIndex_Passed (output)
Tester_StoreyIndex_Passed (output)

FME custom transformer StoreyIndexFinder_2

Note: Transformer från workspace KTH_demohuse_walls_roof_openings släppt under 3-Clause BSD License. / Framtagandet är finansierat av: / Smart Built Environments Testbädd: Smarta plan-, bygg- och förvaltningsprocesser över hela livscykeln. / Projektet Får Jag Lov koordinerat av Boverket.
Note: Connect to UUID creator for the walls (or other feature)
AttributeCreator_StoreyList_Input (input)
    -> AttributeCreator_StoreyList
Note: Connect to ListElementCounter / belonging to IfcBuildingStorey
PythonCaller_2_Input (input)
    -> PythonCaller_2
1 (output)
2 (output)
0 (output)

Bookmark: Adding index per building storey
AttributeCreator_StoreyList
    ATTR_TABLE = SET_TO storeyListIndex
    -> PythonCaller_2
PythonCaller_2
    NEW_ATTRIBUTES = storeyListIndex
    PYTHONSOURCE:
      import fme
      import fmeobjects
      # Template Function interface:
      # When using this function, make sure its name is set as the value of
      # the 'Class or Function to Process Features' transformer parameter
      def processFeature(feature):
          pass


      def listFinder(f): # f - the list with all features
          pos = 0 # Index in list
          while pos < len(f):
              attList = f[pos].getAllAttributeNames() # get all feature attributes
              for att in attList:
                  if 'buildingStoreysID' in att:
                      return f[pos].getAttribute('buildingStoreysID{}.ifc_unique_id')
              pos += 1
          return None

      def storeyIndexFinder(fe,storeyList):
          # Returns the index in the storey list of current feature
          parentID = fe.getAttribute('ifc_parent_unique_id')
          pos = 0
          while pos < len(storeyList):
              if storeyList[pos] == parentID:
                  return pos
              else:
                  pass # Do nothing
              pos += 1

      # Template Class Interface:
      # When using this class, make sure its name is set as the value of
      # the 'Class or Function to Process Features' transformer parameter
      class FeatureProcessor(object):
          def __init__(self):
              self.featureList = []
              self.logger = fmeobjects.FMELogFile()
              # logger.logMessageString('message')

          def input(self,feature): # This function is called every time a feature is added
              self.featureList.append(feature)

          def close(self):
              li = listFinder(self.featureList) # Return a list with storey id
              for f in self.featureList:
                  currIndex = storeyIndexFinder(f, li) # Check feature parent_id against list with storey id
                  f.setAttribute("storeyListIndex", currIndex)
                  self.pyoutput(f)
    PYTHONSYMBOL = FeatureProcessor
    -> Tester_StoreyIndex [off]
    -> TestFilter
TestFilter
    DEFAULT_VALUE = <UNFILTERED>
    TEST_LIST = BOOL_OP,OR,COMPOSITE_TEST,<Unused>,TEST_CLAUSE,"TEST @Value(storeyListIndex) = 1",1,BOOL_OP,OR,COMPOSITE_TEST,<Unused>,TEST_CLAUSE,"TEST @Value(storeyListIndex) = 2",2,BOOL_OP,OR,COMPOSITE_TEST,<Unused>,TEST_CLAUSE,"TEST @Value(storeyListIndex) = 0",0
    1 -> 1 (output)
    2 -> 2 (output)
    0 -> 0 (output)

Bookmark: Tester from KTH_demohouse_..
Note: Which storey index to include
Tester_StoreyIndex [off]
    BOOL_OP = OR
    TEST_MODE = Automatic
    TEST_DESCRIPTION = ""
    TEST_CLAUSE = TEST @Value(storeyListIndex) = 1

FME custom transformer MinZ_4

Input (input)
    -> AttributeCreator
AttributeCreator
    ATTR_TABLE = SET_TO _zminval
    -> BoundsExtractor
BoundsExtractor
    YMAX = _ymax
    YMIN = _ymin
    ZMAX = _zmax
    XMIN = _xmin
    ZMIN = _zmin
    XMAX = _xmax
    -> PythonCaller
PythonCaller
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    PYTHONSYMBOL = FeatureProcessor
    -> Output (output)
Output (output)

FME custom transformer MinZ_3

Input (input)
    -> AttributeCreator
AttributeCreator
    ATTR_TABLE = SET_TO _zminval
    -> BoundsExtractor
BoundsExtractor
    YMAX = _ymax
    YMIN = _ymin
    ZMAX = _zmax
    XMIN = _xmin
    ZMIN = _zmin
    XMAX = _xmax
    -> PythonCaller
PythonCaller
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    PYTHONSYMBOL = FeatureProcessor
    -> Output (output)
Output (output)

FME custom transformer CreateBasisBYA

Parameters:
- IFC_UNIQUE_ID = @Value(ifc_unique_id)   # Ifc Unique Id

Bookmark: BasisBYA
Input_storey (input)
    -> MinZ_2
MinZ_2
    -> SurfaceFootprintReplacer_3
SurfaceFootprintReplacer_3
    SHADOW_MODE = Overhead Shadow
    OFFSET_Z = @Value(_zminval)
    FOOTPRINT -> Snapper
Input_pointCloud (input)
    -> MinZ
Input_facade (input)
    -> MinZ
MinZ
    -> SurfaceFootprintReplacer_2
SurfaceFootprintReplacer_2
    SHADOW_MODE = Overhead Shadow
    OFFSET_Z = @Value(_zminval)
    FOOTPRINT -> HullAccumulator
    <REJECTED> -> SurfaceFootprintReplacer_2__Rejected_
HullAccumulator
    GROUP_BY = ifc_unique_id _zminval
    HULLTYPE_PARAM = Convex ()
    3DMODE_PARAM = 3D
    DEFAULTZ = @Value(_zminval)
    HULL -> Snapper
Dissolver_2
    DEAGGREGATE_INPUT = Yes
    NO_OVRLP = No
    CONNECT_Z_MODE = Extend
    ACCUM_INPUT_ATTRS = Merge Incoming Attributes
    AREA -> BoundsExtractor
BoundsExtractor
    YMAX = _ymax
    YMIN = _ymin
    ZMAX = _zmax
    XMIN = _xmin
    ZMIN = _zmin
    XMAX = _xmax
    -> SurfaceFootprintReplacer
SurfaceFootprintReplacer
    SHADOW_MODE = Overhead Shadow
    OFFSET_Z = @Value(_zminval)
    FOOTPRINT -> DonutHoleExtractor_2
DonutHoleExtractor_2
    DEAGGREGATE_INPUT = Yes
    OUTERSHELL -> Output (output)
Output (output)
SurfaceFootprintReplacer_2__Rejected_: Inspector [off]

Bookmark: Prepare for dissolve
  Snapp areas that won't dissolve (because they don't intersect/ are connected)
Snapper
    CLEANING_TOLERANCE_MODE = AUTO
    TOLERANCE = 10
    SNAPTYPE_PARAM = Segment Snapping
    SNAPPED -> Dissolver_2
    UNTOUCHED -> Dissolver_2

FME custom transformer FootprintAreaCalculator

Parameters:
- IFC_PARENT_UNIQUE_ID = @Value(ifc_parent_unique_id)   # Ifc Parent Unique Id
- IFC_UNIQUE_ID = @Value(ifc_unique_id)   # ifc_unique_id
- ELEVATION = @Value(Elevation)   # Elevation
- IFC_PARENT_ID = @Value(ifc_parent_id)   # Ifc Parent Id
- FloorIndex = 1   # First floor index

All_ListBasedFeatureMerger (input)
    -> ListBasedFeatureMerger [SUPPLIER]
IfSlab_Input (input)
    -> StoreyIndexFinder_2 [AttributeCreator_StoreyList_Input]
BuildingStorey_AggregatedList (input)
    -> StoreyIndexFinder_2 [PythonCaller_2_Input]
StoreyIndexFinder_2
    IFC_UNIQUE_ID = @Value(ifc_unique_id)
    storeyIndex = $(FloorIndex)
    Tester_StoreyIndex_Passed -> CreateBasisBYA [Input_storey]
Note: Clip the building to be able to find the protruding parts.
Clipper_Max_3m_Input (input)
    -> Clipper_Max_3m_2
Clipper_Max_5m_Input (input)
    -> Clipper_Max_5m_3
Clipper_BottomEdge_Input (input)
    -> Clipper_BottomEdge_2
Note: Clip lowest part of the wall
Clipper_BottomEdge_2: Building_Clipper
    OFFSET_Z = @Value(Elevation)
    DISTANCE = 10
    IFC_PARENT_UNIQUE_ID = @Value(ifc_parent_unique_id)
    Output_extruded -> PointCloudClipper [Clipper]
    Output_clipper -> CreateBasisBYA [Input_facade]
    Rejected -> PointCloudClipper [Wall]
Note: Handle wall objects that won't clip with default FME Clipper
PointCloudClipper
    IFC_UNIQUE_ID = @Value(ifc_unique_id)
    IFC_PARENT_UNIQUE_ID = @Value(ifc_parent_unique_id)
    Output_2D -> CreateBasisBYA [Input_pointCloud]
CreateBasisBYA
    IFC_UNIQUE_ID = @Value(ifc_unique_id)
    -> AttributeManager_2
    -> Protruding_Part [Bufferer_Input]
    -> SurfaceFootprintReplacer_3
SurfaceFootprintReplacer_3
    SHADOW_MODE = Overhead Shadow
    OFFSET_Z = 0
    FOOTPRINT -> Snapper
Note: Calculate BUA, / scale from mm2 to m2
AreaCalculator
    MULT = 1/1000000
    AREA_ATTR = _area
    AREA_TYPE = Plane Area
    -> AttributeRounder
Note: Round to on dec.
AttributeRounder
    SRC_ATTRS = _area
    PLACES = 1
    ROUND_TYPE = Nearest
    -> AttributeKeeper_2
AttributeKeeper_2
    KEEP_ATTRS = _area
    -> FootprintArea (output)
FootprintArea (output)

Bookmark: Klipper byggnaden 0-3 m
Clipper_Max_3m_2: Building_Clipper
    OFFSET_Z = @Value(Elevation)
    DISTANCE = 3000
    IFC_PARENT_UNIQUE_ID = @Value(ifc_parent_unique_id)
    Output_extruded -> PointCloudClipper_5 [Clipper]
    Output_clipper -> Protruding_Part [Clipper_Byggnad]
    Rejected -> PointCloudClipper_5 [Wall]
PointCloudClipper_5
    IFC_UNIQUE_ID = @Value(ifc_unique_id)
    IFC_PARENT_UNIQUE_ID = @Value(ifc_parent_unique_id)
    Output_3D -> Protruding_Part [Clipper_Byggnad]

Bookmark: Klipper byggnaden 3-5 m
Clipper_Max_5m_3: Building_Clipper
    OFFSET_Z = @Value(Elevation)+3000
    DISTANCE = 2000
    IFC_PARENT_UNIQUE_ID = @Value(ifc_parent_unique_id)
    Output_extruded -> PointCloudClipper_6 [Clipper]
    Output_clipper -> Protruding_Part_2 [Clipper_Byggnad]
    Rejected -> PointCloudClipper_6 [Wall]
PointCloudClipper_6
    IFC_UNIQUE_ID = @Value(ifc_unique_id)
    IFC_PARENT_UNIQUE_ID = @Value(ifc_parent_unique_id)
    Output_3D -> Protruding_Part_2 [Clipper_Byggnad]

Bookmark: 0-3m, < 0,5m
Protruding_Part
    _ZMIN = @Value(_zmin)
    _ZMINVAL = @Value(_zminval)
    DISTANCE = 3000
    OFFSET = 500
    Output_Outside -> Aggregator

Bookmark: 3-5m, < 1,5m
Note: Flytta zmin +3000mm
AttributeManager_2
    ATTR_TABLE:
      SET_TO _zminval = @Value(_zminval)+3000
      SET_TO _zmin = +3000
    -> Protruding_Part_2 [Bufferer_Input]
Protruding_Part_2
    _ZMIN = @Value(_zmin)
    _ZMINVAL = @Value(_zminval)
    DISTANCE = 2000
    OFFSET = 1500
    Output_Outside -> Aggregator

Bookmark: Protruding parts
Note: Clip protruding parts (Output_Outside)
Aggregator
    SEP = ,
    MODE = Attributes Only
    LIST_ATTRS_TO_INCLUDE = ifc_unique_id
    LIST_NAME = ListName
    CONCAT_ATTRS = ifc_unique_id
    ACCUM_ATTRS_NAME = Merge Incoming Attributes
    ORDERED = No
    AGGREGATE -> ListElementCounter
ListElementCounter
    LIST_NAME = ListName{}
    CNT_ATTR = nbrStoreys
    -> ListBasedFeatureMerger [REQUESTOR]
Note: Retrive the whole protruding object with ifc_unique_id, project and merge with "BasisBUA"
ListBasedFeatureMerger
    PROCESS_DUPS = Yes
    BUILD_INCOMPLETE = Merge Supplier Information
    REFEEATTR = @Value(ifc_unique_id)
    MODE = AUTO
    MERGE_TYPE = Geometry
    REFERATTR = ListName{}.ifc_unique_id
    GEOM_TYPE = Build Aggregates
    MERGED -> SurfaceFootprintReplacer_2
SurfaceFootprintReplacer_2
    SHADOW_MODE = Overhead Shadow
    OFFSET_Z = 0
    FOOTPRINT -> Snapper
Dissolver_2
    DEAGGREGATE_INPUT = Yes
    NO_OVRLP = No
    CONNECT_Z_MODE = First Wins
    ACCUM_INPUT_ATTRS = Use Attributes From One Feature
    AREA -> AreaCalculator

Bookmark: Prepare for dissolve
  Snapp areas that won't dissolve (because they don't intersect/ are connected)
Snapper
    CLEANING_TOLERANCE_MODE = AUTO
    TOLERANCE = 10
    SNAPTYPE_PARAM = Segment Snapping
    SNAPPED -> Dissolver_2
    UNTOUCHED -> Dissolver_2

FME custom transformer Building_Clipper_2

Parameters:
- IFC_PARENT_UNIQUE_ID = @Value(ifc_parent_unique_id)   # Ifc Parent Unique Id
- DISTANCE = 10   # Distance
- OFFSET_Z = 0   # Z" Elevation

Input (input)
    -> Deaggregator
    -> BoundsExtractor
    -> BoundingBoxAccumulator
    -> Input
BoundingBoxAccumulator
    ATTR_NAME = _topferIndex
    DESTINATION_SCALE = 1
    TOPFER_INDEX = No
    SOURCE_SCALE = 1
    ACCUM_ATTRS_NAME = Use Attributes From One Feature
    BOUNDING_BOX -> FeatureMerger [REQUESTOR]
BoundsExtractor
    YMAX = _ymax
    YMIN = _ymin
    ZMAX = _zmax
    XMIN = _xmin
    ZMIN = _zmin
    XMAX = _xmax
    -> ListBuilder
ListBuilder
    LIST_ATTRS_TO_INCLUDE = _zmin ifc_parent_unique_id
    LIST_NAME = _list
    GROUPS_ORDERED = No
    -> ListRangeExtractor
ListRangeExtractor
    MIN = _min
    SRC_LIST = _list{}._zmin
    MAX = _max
    -> FeatureMerger [SUPPLIER]
FeatureMerger
    ATTR_CONFLICT_RES = Use Requestor
    ATTR_ACCUM_MODE = Merge Supplier
    PROCESS_DUPS = No
    SUPPLIERS_FIRST = No
    IGNORE_NULLS = No
    REJECT_NULL_MISSING_KEYS = No
    MERGE_TYPE = Attributes Only
    JOIN_KEYS = @Value(ifc_parent_unique_id) @Value(_list{0}.ifc_parent_unique_id) AUTO
    MERGED -> SurfaceFootprintReplacer
SurfaceFootprintReplacer
    SHADOW_MODE = Overhead Shadow
    OFFSET_Z = $(OFFSET_Z)+@Value(_min)
    FOOTPRINT -> Extruder
Extruder
    DIRECTION = Vertical
    DISTANCE = $(DISTANCE)
    EXTRUDED -> Clipper_2 [CLIPPER]
    EXTRUDED -> Output_extruded (output)
Output_extruded (output)
Deaggregator
    EXPLODE_INSTANCES = No
    CHILD_ID_ATTR = _hierarchy_child_id_list
    PART_NUMBER_FIELD = _part_number
    ID_ATTR = _hierarchy_id
    MODE = Flatten One Level
    COPY_ATTR = Every Node
    PARENT_ID_ATTR = _hierarchy_parent_id
    ID_SELECTION = ID and Parent ID
    SPLIT_COMPOSITES = No
    LIST_ATTR_MODE_LOOKUP = LEAN
    GEOM_NAME_FIELD = _geometry_name
    DEAGGREGATED -> GeometryFilter
GeometryFilter
    BREAK_AGG = No
    GEOM_PORT_NAMES = Solid
    SOLID -> Clipper_2 [CLIPPEE]
Clipper_2
    CLIPPED_ATTR = _clipped
    PRESERVE_CLIPPEE_EXTENTS = No
    CREATE_AGGREGATES = Yes
    LINES_AS_SEGMENTS = No
    BOUNDARY_CASES = Treat as Inside
    CLIP_TYPE = Multiple Clippers
    MISSING_VAL_MODE = Compute
    VAL_SOURCE = Clippee Only
    MEASURE_TYPE = Continuous
    INSIDE -> Output_clipper (output)
    <REJECTED> -> Rejected (output)
Output_clipper (output)
Rejected (output)
Input: Inspector [off]

FME custom transformer Protruding_Part

Parameters:
- _ZMINVAL = @Value(_zminval)   # Zminval
- OFFSET = 500   # Buffer Amount
- DISTANCE = 3000   # Distance
- _ZMIN = @Value(_zmin)   # Zmin

Bufferer_Input (input)
    -> Bufferer
Clipper_Byggnad (input)
    -> Clipper [CLIPPEE]
Clipper
    CLIPPED_ATTR = _clipped
    ATTR_CONFLICT_RES = Use Clippee
    PRESERVE_CLIPPEE_EXTENTS = No
    ATTR_ACCUM_MODE = Merge Clipper
    CREATE_AGGREGATES = Yes
    LINES_AS_SEGMENTS = No
    BOUNDARY_CASES = Treat as Inside
    CONNECT_Z_MODE = First Wins
    CLIP_TYPE = Multiple Clippers
    MISSING_VAL_MODE = Compute
    VAL_SOURCE = Clippee Only
    MEASURE_TYPE = Continuous
    DEFAULT_VAL = 0
    INSIDE -> Output_Inside (output)
    OUTSIDE -> GeometryValidator
    <REJECTED> -> Clipper__Rejected_
Output_Inside (output)
Note: Kontrollera så att objekten har geometri
GeometryValidator
    CONNECT_Z_MODE_TR = First Wins
    ISSUE_ATTR_NAME = _issues
    TYPE_REPAIR = TYPE_REPAIR
    AREA_ORIENTATION = AREA_ORIENTATION
    PRESETS = Basic Geometry Integrity
    SUMMARY = Detailed
    REPAIR = Yes
    NULL_REMOVAL = NULL_REMOVAL
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    ARC_ENDPOINT_TOLERANCE_MODE = Auto
    ORIENTATION_CHECK_DIR = Valid
    NAN_REMOVAL = NAN_REMOVAL
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    CORNER_STYLE = Round
    ANGLE = 1
    CAP_STYLE = Round
    OFFSET = $(OFFSET)
    BUFFERED -> SurfaceFootprintReplacer
    BUFFERED -> Bufferer_Buffered
Bufferer_Buffered: Inspector [off]
SurfaceFootprintReplacer
    SHADOW_MODE = Overhead Shadow
    OFFSET_Z = @Value(_zminval)
    FOOTPRINT -> Extruder
Note: Extrude 3 el 2 m
Extruder
    DIRECTION = Auto
    DISTANCE = $(DISTANCE)
    EXTRUDED -> Clipper [CLIPPER]
    <REJECTED> -> Extruder__Rejected_
Extruder__Rejected_: Inspector

FME custom transformer MinZ_2

Input (input)
    -> AttributeCreator
AttributeCreator
    ATTR_TABLE = SET_TO _zminval
    -> BoundsExtractor
BoundsExtractor
    YMAX = _ymax
    YMIN = _ymin
    ZMAX = _zmax
    XMIN = _xmin
    ZMIN = _zmin
    XMAX = _xmax
    -> PythonCaller
PythonCaller
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    PYTHONSYMBOL = FeatureProcessor
    -> Output (output)
Output (output)
