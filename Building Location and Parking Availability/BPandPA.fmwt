FME workspace BPandPA.fmwt
Title: BPandPA

Parameters:
- SourceDataset_GML_5 = $(FME_MF_DIR)detaljPlanReader/hoganas.xml   # Source Geography Markup Language (GML) File(s)
- SourceDataset_XML = $(FME_MF_DIR)detaljPlanReader/hoganas.xml   # Source XML File(s)
- DestDataset_OGCKML = $(FME_MF_DIR)detaljPlanReader/detaljplanSchema\hoganas.kml   # Destination Google KML File
- SourceDataset_ESRISHAPE = $(FME_MF_DIR)Hjaltevad168/Hjaltevad168.shp   # Source Esri Shapefile(s)
- min_dist = 3   # " " min_dist_build
- SourceDataset_ESRISHAPE_4 = $(FME_MF_DIR)Viakop_313_fast/Viakop_313_fast.shp   # Source Esri Shapefile(s)

Readers:
- GML_1: GML from $(SourceDataset_GML_5) in SWEREF-99-18-00
- XML_1: XML from $(SourceDataset_XML) in SWEREF-99-18-00
- ESRISHAPE_1: ESRISHAPE from $(SourceDataset_ESRISHAPE)
- ESRISHAPE_2: ESRISHAPE from $(SourceDataset_ESRISHAPE_4)

Writers:
- OGCKML_1: OGCKML to $(DestDataset_OGCKML) in SWEREF-99-13-30

Note: De-buffer the house , only for this transformer
Bufferer
    ANGLE = 22.5
    CAP_STYLE = Round
    CORNER_STYLE = Round
    MODE = AREA
    OFFSET = -0.001
    BUFFERED -> SpatialFilter_4 [Filter]
Viakop_313_fast: Inspector
Note: Workspace för att importera en detaljplan enligt SS 637040. / Polygoner för områden i detaljplanen skapas och bestämmelser kopplas till polygonerna. Workspacet hanterar inte kartografin utan ska ses som ett verktyg för att hantera bestämmelser vid kontroll av bygglov. Bestämmelser och information som gäller för hela planen kopplas inte till något område. / Endast ett hål per polygon hanteras i nuvarande version.
Note: This workspace is released under the 3-Clause BSD License. For details, see https://opensource.org/licenses/BSD-3-Clause / Framtagandet är finansierat av: / Smart Built Environments Testbädd: Smarta plan-, bygg- och förvaltningsprocesser över hela livscykeln. / Projektet Får Jag Lov koordinerat av Boverket. / Höganäs kommun har bidragit med detaljplanen som bifogas som testdata. / Copyright (c) 2018, Lunds universitet / All rights reserved.
CsmapReprojector
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> FeatureMerger [SUPPLIER]
CsmapReprojector_2
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> Aggregator
CsmapReprojector_3
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> Aggregator
Note: Create list with gränser per område
Aggregator
    ACCUM_ATTRS_NAME = Merge Incoming Attributes
    GROUP_BY = xml_parent_id
    LIST_ATTRS_TO_INCLUDE = minus.href plus.href xml_parent_child_pos
    LIST_NAME = childList
    MODE = Attributes Only
    ORDERED = No
    SEP = ,
    AGGREGATE -> PolygonCreator
CsmapReprojector_4
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> AttributeCreator_2
Note: Create ID for later join
AttributeCreator_2
    ATTR_TABLE = SET_TO ID_join = #@Value(gml_id)
    -> PolygonCreator
Note: Creates polygons over Områden. / NB, current version handles max. one hole / per polygon, need to modify in case polygons / with more than one hole exists.
PolygonCreator: PythonCaller
    PYTHONSOURCE:
      import fme
      import fmeobjects

      # Finds and returns the requested gräns
      def gransFinder(id,gransList):
          for grans in gransList:
              if grans.getAttribute('ID_join') == id:
                  return grans

      # Finds first line segment, either outer or inner polygon
      def initialBoundaryLine(polygonBoundaryParts):
          geo = polygonBoundaryParts.getGeometry()
          #print polygonBoundaryParts.getGeometryType()

          nbrLines = geo.numParts()

           # Taking first part of the FMEPath
          polygonBoundary = geo.getPartAt(0)

          if type(polygonBoundary) == fmeobjects.FMEArc:
              polygonBoundary = polygonBoundary.getAsLine()

          #Iterating over the rest of the part in the FMEPath object
          for p in xrange(1,nbrLines):
              tp = geo.getPartAt(p)
              if type(tp) == fmeobjects.FMEArc: # Needs FMELine
                  tp = tp.getAsLine()

              polygonBoundary.appendLine(tp)

          return polygonBoundary

      # NB!, handles polygons with zero or one hole, not more than one hole.
      class FeatureProcessor(object):
          def __init__(self):
              self.omrade = []
              self.grans = []

          # Saving in different lists depending on if the feature is a gräns or område
          def input(self,feature):
              if feature.hasGeometry():
                  self.grans.append(feature)
              else:
                  self.omrade.append(feature)

          def close(self):
              # Iterating over all Område sent to the PythonCaller
              for omr in self.omrade:
                  tempGrans = True # Will stop the loop after last item is found (temp = None)
                  index = 0 # Index of "Gräns"
                  innerIndex = 0 # For keeping track of holes

                  #Looping over all "gränser" in current "Område"
                  while tempGrans != None:
                      tempGrans = omr.getAttribute('childList{%i}.xml_parent_child_pos' % (index))
                      # Already found last "gräns" of the "område"
                      if not tempGrans:
                          break
                      tempGrans = int(tempGrans)

                      if not tempGrans == index: # To break in case something is wrong wth indices
                          print 'Index not correct'
                          break
                      # Retreiving the next segment and finding direction.
                      minusTest = omr.getAttribute('childList{%i}.minus.href' % (index))
                      if minusTest != None:
                          minus = True
                          tempGransID = minusTest
                      else:
                          minus = False
                          tempGransID = omr.getAttribute('childList{%i}.plus.href' % (index))

                      # Building line
                      # This part is for the first "Gräns" either in the outer (index == 0) polygon or
                      # a hole (innerIndex == 1)
                      if index == 0 or innerIndex == 1: # This case should be handled before the loop starts............
                          if index == 0:
                              partOne = gransFinder(tempGransID,self.grans)
                              polygonBoundary = initialBoundaryLine(partOne)
                              if minus:
                                  polygonBoundary.reverse()

                          # If a hole was found
                          elif innerIndex == 1: # This case should be handled before the loop starts............
                              partOne = gransFinder(tempGransID,self.grans)
                              polygonBoundary = initialBoundaryLine(partOne)
                              if minus:
                                  polygonBoundary.reverse()
                              innerIndex += 1

                      # From the second "gräns" in the list.
                      else:
                          polygonBoundaryParts = gransFinder(tempGransID,self.grans)

                          geo = polygonBoundaryParts.getGeometry()

                          nbrLines = geo.numParts()

                          tmpLine = geo.getPartAt(0)
                          if type(tmpLine) == fmeobjects.FMEArc:
                              tmpLine = tmpLine.getAsLine()

                          #Iterating over the of the parts in the FMEPath object
                          for p in xrange(1,nbrLines):
                              tp = geo.getPartAt(p)
                              if type(tp) == fmeobjects.FMEArc:
                                  tp = tp.getAsLine()
                              tmpLine.appendLine(tp)
                          if minus:
                              tmpLine.reverse()
                          polygonBoundary.appendLine(tmpLine)
                          # True of a closed polygon is found.
                          if polygonBoundary.isClosed(False) and innerIndex == 0: # False => not considering 3D
                              innerIndex = 1
                              outerPoly = fmeobjects.FMEDonut(polygonBoundary)
                              polygonBoundary = None

                      index += 1

                  if innerIndex > 1: # Hole was found (innerIndex == 1 => only closed poly)
                      innerPoly = fmeobjects.FMEDonut(polygonBoundary)
                      outerPoly.addInnerBoundaryCurve(polygonBoundary)
                  elif index == 1:
                      outerPoly = fmeobjects.FMEDonut(polygonBoundary)

                  omr.setGeometry(outerPoly)

                  self.pyoutput(omr)
    PYTHONSYMBOL = FeatureProcessor
    -> FeatureMerger_2 [REQUESTOR]
CsmapReprojector_5
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> DP_Planbestammelse
DP_Planbestammelse: Inspector
CsmapReprojector_6
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> GeometryFilter
    REPROJECTED -> FeatureMerger_Egenskap [SUPPLIER]
Note: OBS!!!!!!!!!!!!! / Hanteringen av områden som är tillåtna att bebygga fungerar enbart om beteckning är n. Detta måste troligen hanteras olika i de flesta fall!!!!!!!!!!!!!! / Justera i Bookmark "Finds area where buildings are permitted" / Connect AttributeRemover_2 to PointOnAreaOverlayer (port: Area). / Modify PythonCaller_Nockhojd to initiate maxNock = None
GeometryFilter
    BREAK_AGG = No
    GEOM_PORT_NAMES = Point
    POINT -> PointOnAreaOverlayer [POINT]
    <UNFILTERED> -> GeometryFilter_2
Note: Unfiltered, regulations with link, no geometry.
GeometryFilter_2
    BREAK_AGG = No
    GEOM_PORT_NAMES = Line Arc
    LINE -> Bestammelser_line
    <UNFILTERED> -> FeatureMerger_4 [SUPPLIER]
Bestammelser_line: Inspector
CsmapReprojector_7
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> DP_Plan
DP_Plan: Inspector
CsmapReprojector_8
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> FeatureMerger [REQUESTOR]
Note: Needs xml_id from the / XML-reader to join with lines.
FeatureMerger
    ATTR_ACCUM_MODE = Merge Supplier
    ATTR_CONFLICT_RES = Use Requestor
    CLEANING_TOLERANCE = None
    IGNORE_NULLS = No
    JOIN_KEYS = @Value(gml_id) @Value(DP_Omrade.id) AUTO
    MERGE_TYPE = Attributes Only
    PROCESS_DUPS = No
    REJECT_NULL_MISSING_KEYS = No
    SUPPLIERS_FIRST = No
    MERGED -> AttributeKeeper
AttributeKeeper
    KEEP_ATTRS = xml_id,gml_id,xml_fragment,DP_Omrade.id,gml_parent_id
    -> AttributeCreator
AttributeCreator
    ATTR_TABLE = SET_TO ID_join = #@Value(DP_Omrade.id)
    -> FeatureMerger_Egenskap [REQUESTOR]
CsmapReprojector_9
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> DP_Data
DP_Data: Inspector
CsmapReprojector_10
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> FeatureMerger_Anvandning [SUPPLIER]
AttributeRemover
    REMOVE_ATTRS = minus,plus
    -> FeatureMerger_2 [SUPPLIER]
Note: Adding Geometries to bestämmelser
FeatureMerger_2
    ATTR_ACCUM_MODE = Merge Supplier
    ATTR_CONFLICT_RES = Use Requestor
    CLEANING_TOLERANCE = None
    IGNORE_NULLS = No
    JOIN_KEYS = @Value(xml_parent_id) @Value(xml_id) AUTO
    MERGE_TYPE = Attributes and Geometry
    PROCESS_DUPS = No
    REJECT_NULL_MISSING_KEYS = No
    SUPPLIERS_FIRST = No
    MERGED -> AttributeRemover_2
    MERGED -> FeatureMerger_3 [REQUESTOR]
AttributeRemover_2
    LIST_ATTRS = childList{}
    REMOVE_ATTRS = xml_id,gml_id,xml_parent_child_pos,ID_join,plus.href,xml_matched_element,plus,minus.href,linje
    -> Tester
Note: Merging attributes from / areas allowed to build.
FeatureMerger_3
    ATTR_ACCUM_MODE = Merge Supplier
    ATTR_CONFLICT_RES = Use Requestor
    CLEANING_TOLERANCE = None
    IGNORE_NULLS = No
    JOIN_KEYS = @Value(DP_Omrade.id) @Value(DP_Omrade.id) AUTO
    MERGE_TYPE = Attributes Only
    PROCESS_DUPS = No
    REJECT_NULL_MISSING_KEYS = No
    SUPPLIERS_FIRST = No
    MERGED -> min_dist_building
    UNMERGED_REQUESTOR -> FeatureMerger_4 [REQUESTOR]
Note: Merging with bestämmelser without geometry. / Areas not allowed to build (prickad mark)
FeatureMerger_4
    ATTR_ACCUM_MODE = Merge Supplier
    ATTR_CONFLICT_RES = Use Requestor
    CLEANING_TOLERANCE = None
    IGNORE_NULLS = No
    JOIN_KEYS = @Value(omrade.xlink_href) @Value(omrade.xlink_href) AUTO
    MERGE_TYPE = Attributes and Geometry
    PROCESS_DUPS = No
    REJECT_NULL_MISSING_KEYS = No
    SUPPLIERS_FIRST = No
    MERGED -> FeatureColorSetter_NotAllowedToBuild
    UNMERGED_REQUESTOR -> TestFilter
FeatureColorSetter_NotAllowedToBuild
    COLOR = 0,0,0
    FILL_COLOR = 1,0.14902,0.160784
    MODE = Fixed
    COLORED -> Not_allowed_to_build_prickad_mark_
Not_allowed_to_build_prickad_mark_: Inspector
TestFilter
    DEFAULT_VALUE = <UNFILTERED>
    TEST_LIST = BOOL_OP,OR,COMPOSITE_TEST,<Unused>,TEST_CLAUSE,"TEST @Value(anvandningsslag) CONTAINS gata",Gata,BOOL_OP,OR,COMPOSITE_TEST,<Unused>,TEST_CLAUSE,"TEST @Value(anvandningsslag) CONTAINS gang",Gång,BOOL_OP,OR,COMPOSITE_TEST,<Unused>,TEST_CLAUSE,"TEST @Value(anvandningsslag) CONTAINS cykel",Cykel,BOOL_OP,OR,COMPOSITE_TEST,<Unused>,TEST_CLAUSE,"TEST @Value(beteckning) CONTAINS vatten",Vatten
    Gata -> FeatureColorSetter_Gata_gang
    Gång -> FeatureColorSetter_Gata_gang
    Cykel -> FeatureColorSetter_Gata_gang
    Vatten -> FeatureColorSetter_Vatten
    <UNFILTERED> -> FeatureColorSetter_OtherAreas
FeatureColorSetter_Gata_gang
    COLOR = 0.666667,0.556863,0.552941
    FILL_COLOR = 0.666667,0.556863,0.552941
    MODE = Fixed
    COLORED -> Gata_gang
    COLORED -> Dissolver_2
    COLORED -> VertexExtractor
Gata_gang: Inspector
VertexExtractor
    Point -> VertexExtractor_Point
VertexExtractor_Point: Inspector
Note: Dissolves the polygons into 1 big polygon
Dissolver_2
    ACCUM_INPUT_ATTRS = Use Attributes From One Feature
    CLEANING_TOLERANCE = None
    CONNECT_Z_MODE = First Wins
    DEAGGREGATE_INPUT = Yes
    NO_OVRLP = No
    AREA -> Generalizer_2
FeatureColorSetter_Vatten
    COLOR = 0,0,1
    FILL_COLOR = 0,0,1
    MODE = Fixed
    COLORED -> Water
Water: Inspector
FeatureColorSetter_OtherAreas
    COLOR = 0,0,0
    FILL_COLOR = 0.666667,1,0.498039
    MODE = Fixed
    COLORED -> Other_areas
Other_areas: Inspector
min_dist_building: AttributeCreator
    ATTR_TABLE = SET_TO min_dist = $(min_dist)
    -> FeatureColorSetter_AreasAllowedToBuild
FeatureColorSetter_AreasAllowedToBuild
    COLOR = 0,0,0
    FILL_COLOR = 1,1,0
    MODE = Fixed
    COLORED -> Areas_allowed_to_build
    COLORED -> MinDistance [SpatialFilter_Candidate]
    COLORED -> AreaOnAreaOverlayer [AREA]
Areas_allowed_to_build: Inspector
Tester_4
    BOOL_OP = OR
    TEST_CLAUSE = TEST @Value(_overlaps) = 2
    PASSED -> Tester_2
    PASSED -> Tester_5
Note: Check if house height is according to standard
Tester_2
    BOOL_OP = OR
    TEST_CLAUSE = TEST @Value(hojdvarde) <= @Value(max_nock)
    PASSED -> BuildingHeight_OK
    FAILED -> BuildingHeight_NotOK
BuildingHeight_OK: Inspector
BuildingHeight_NotOK: Inspector
Note: Check if roof angle is according to standard
Tester_5
    BOOL_OP = OR
    TEST_CLAUSE:
      TEST @Value(takvinkel) <= @Value(max_takvinkel)
      TEST max_takvinkel ATTRIBUTE_IS_MISSING ""
    PASSED -> RoofAngle_OK
    FAILED -> RoogAngle_notOK
RoofAngle_OK: Inspector
RoogAngle_notOK: Inspector
MinDistance
    MIN_DIST = @Value(min_dist)
    SpatialFilter3 -> LineIntersectBuffer [Clipper_3_Clipper]
    SpatialFilter3 -> AreaGapAndOverlapCleaner
    Tester_2_Passed -> Chopper_4
    Tester_2_Failed -> Chopper
    Tester_2_Failed -> Clipper_2 [CLIPPER]
Note: If testpasses, convert the polygon into individual lines
Chopper_4
    DEAGGREGATE_INPUT = Deaggregate
    MAX_VERTICES = 2
    MODE = By Vertex
    REMNANT_ATTR = _remnant
    CHOPPED -> LinesOk_2
Note: Green if lines are according to standard
LinesOk_2: FeatureColorSetter
    COLOR = 0,0.666667,0
    MODE = Fixed
    COLORED -> LinesOk_2_Colored
LinesOk_2_Colored: Inspector
Note: If test failes, convert the polygon into individual lines
Chopper
    DEAGGREGATE_INPUT = Deaggregate
    MAX_VERTICES = 2
    MODE = By Vertex
    REMNANT_ATTR = _remnant
    CHOPPED -> NeighborFinder_2 [BASE]
Note: Finds the lines that do not meet the minimum distance requirement.
NeighborFinder_2
    CANDIDATES_FIRST = No
    INSERT_VERTEX = No
    MAX = $(min_dist)
    MEASURES_FROM_CANDIDATE = Yes
    MEASURE_TYPE = Continuous
    MODE = Bases and Candidates
    TREAT_POLYGON_AS = Lines
    MATCHED -> AttributeCreator_3
    UNMATCHED_BASE -> LinesOk
Note: Calculate how many meters to move the house to make it acceptable for minimum distance requirement.
AttributeCreator_3
    ATTR_TABLE = SET_TO Dist_to_move = @Evaluate(@sub(@Value(min_dist),@Value(_distance)))
    -> LineNotOk
Note: Red if line(s) are NOT according to standard
LineNotOk: FeatureColorSetter
    COLOR = 0.666667,0,0
    MODE = Fixed
    COLORED -> LineNotOk_Colored
    COLORED -> Bufferer_2
LineNotOk_Colored: Inspector
Note: Create a buffer so it is easier to visualize why the house distance is not according to standard.
Bufferer_2
    ANGLE = 22.5
    CAP_STYLE = None
    CORNER_STYLE = Round
    MODE = AREA
    OFFSET = $(min_dist)
    BUFFERED -> Clipper_2 [CLIPPEE]
Note: buffer should only extend to property area
Clipper_2
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> Buffer_color
Buffer_color: FeatureColorSetter
    COLOR = 1,0,0
    FILL_COLOR = 1,0.666667,0.67451
    MODE = Fixed
    COLORED -> NoBuildZone
NoBuildZone: Inspector
Note: Green if lines are according to standard
LinesOk: FeatureColorSetter
    COLOR = 0,0.666667,0
    MODE = Fixed
    COLORED -> LinesOk_Colored
LinesOk_Colored: Inspector
Note: CUSTOME TRANSFORMER
RectangleCreater
    UNIQUEID = @Value(UniqueID)
    Rectangles -> VertexCounter
    Rectangles -> RectangleCreater_Rectangles
RectangleCreater_Rectangles: Inspector
Note: check if polygons are rectangle or triangle
VertexCounter
    CNT_ATTR = _coordcount
    -> Tester_8
    -> Tester_14
Note: coorcount >= 5 is rectangle, suitable for parking
Tester_14
    BOOL_OP = OR
    TEST_CLAUSE = TEST @Value(_coordcount) >= 5
    PASSED -> SpatialFilter_5 [Candidate]
Note: Is the house and potential parking space disjoint? If yes, then make sure the area is rectangle
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = DISJOINT
    USE_BOUNDING_BOX = No
    PASSED -> SpatialFilter_5_Passed
    PASSED -> Cal_length [LengthCalculator_2_Input]
    FAILED -> SpatialFilter_5_Failed
    FAILED -> Clipper [CLIPPEE]
    FAILED -> AreaOnAreaOverlayer_3 [AREA]
    FAILED -> HouseIntersection [PolygonCutter_Polygons_1]
SpatialFilter_5_Passed: Inspector
Cal_length
    Yes_Park -> YesPark_3
    No_Park -> NoPark_3
YesPark_3: Inspector
NoPark_3: Inspector
SpatialFilter_5_Failed: Inspector
Clipper
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> Chopper_2
HouseIntersection
    UNIQUEID = @Value(UniqueID)
    _CLIPPED = @Value(_clipped)
    _COORDCOUNT = @Value(_coordcount)
    _OVERLAPS = @Value(_overlaps)
    _PREDICATE = @Value(_predicate)
    _REMNANT = @Value(_remnant)
    PolygonCutter_Cut_1 -> SpatialFilter_4 [Candidate]
Note: Find the polygons that intersects the house
SpatialFilter_4
    AGGREGATE_HANDLING = Yes
    BASE_TYPE = Single Filter
    CURVE_BOUNDARY_RULE_PARAM = Default Rule
    PASS_CRITERIA = Pass Against One Filter
    PREDATTR = _predicate
    PREDICATES = INTERSECTS
    USE_BOUNDING_BOX = No
    PASSED -> Dissolver
    FAILED -> SpatialFilter_9 [Filter] [off]
    FAILED -> SpatialFilter_9 [Candidate] [off]
    FAILED -> Cal_length_3 [LengthCalculator_2_Input]
Note: Dissolve these polygons into one big polygon
Dissolver
    ACCUM_INPUT_ATTRS = Use Attributes From One Feature
    CLEANING_TOLERANCE = None
    CONNECT_Z_MODE = First Wins
    DEAGGREGATE_INPUT = Yes
    GROUP_BY = UniqueID
    NO_OVRLP = No
    AREA -> NoPark_2
Note: Since the house is there, there is no space for parking. Mark as red.
NoPark_2: FeatureColorSetter
    COLOR = 0.666667,0,0
    FILL_COLOR = 1,0,0.498039
    MODE = Fixed
    COLORED -> NO_Space_for_parking
Note: Add message in the attribute table
NO_Space_for_parking: AttributeCreator
    ATTR_TABLE = SET_TO Parking = There is no space for parking
    -> NoPark_2_Colored
NoPark_2_Colored: Inspector
Cal_length_3
    Yes_Park -> YesPark
    No_Park -> NoPark
YesPark: Inspector
NoPark: Inspector
Note: Check if there are tiny polygons next to each other, as a way to check for unnecessary nodes
SpatialFilter_9
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = TOUCHES
    USE_BOUNDING_BOX = No
    PASSED -> Dissolver_3
Note: Combine tiny polygons created by unnecessary nodes
Dissolver_3
    ACCUM_INPUT_ATTRS = Use Attributes From One Feature
    CLEANING_TOLERANCE = None
    CONNECT_Z_MODE = First Wins
    DEAGGREGATE_INPUT = Yes
    NO_OVRLP = No
    AREA -> Cal_length_4 [LengthCalculator_2_Input]
Cal_length_4
    Yes_Park -> YesPark_4
    No_Park -> NoPark_6
YesPark_4: Inspector
NoPark_6: Inspector
Note: coodcount = 4 is triangle, not suitable for parking
Tester_8
    BOOL_OP = OR
    TEST_CLAUSE = TEST @Value(_coordcount) = 4
    PASSED -> NoPark_4
Note: Triangle is not suitable for parking, mark as red.
NoPark_4: FeatureColorSetter
    COLOR = 0.666667,0,0
    FILL_COLOR = 1,0,0.498039
    MODE = Fixed
    COLORED -> NO_Space_for_parking_2
Note: Add message in the attribute table
NO_Space_for_parking_2: AttributeCreator
    ATTR_TABLE = SET_TO Parking = There is no space for parking
    -> NoPark_4_Colored
NoPark_4_Colored: Inspector
Python_Out: Inspector
Python_in: Inspector
CsmapReprojector_11
    DEST = SWEREF-99-13-30
    INTERPOLATION_TYPE_NAME = Nearest Neighbor
    RASTER_CELL_SIZE = Preserve Cells
    RASTER_TOLERANCE = 0.0
    VERTICAL_HANDLING = Ignore heights and leave them unchanged
    REPROJECTED -> DP_AdministrativBestammelse
DP_AdministrativBestammelse: Inspector

Bookmark: Min: house position
Hjaltevad168 (reader ESRISHAPE_1)
    attributes: byAndamal char(200), byAndamalD char(200), byArea char(200), hogstaHojd char(200), lagstaHojd char(200), hojdvarde char(200), lagePlan char(200), takvinkel char(200)
    -> Offset_to_origin
Offset_to_origin: Offsetter
    MODE = Cartesian Coordinate
    XOFF = -17
    YOFF = -547
    ZOFF = 0
    OFFSET -> Rotator
Rotator
    ANGLE = 30
    XORIG = 0
    YORIG = 0
    ROTATED -> Offset_to_location
Note: CHANGE COORDINATES HERE!!!!!
Offset_to_location: Offsetter
    MODE = Cartesian Coordinate
    XOFF = 102125
    YOFF = 6234106
    ZOFF = 0
    OFFSET -> AreaOnAreaOverlayer [AREA]
    OFFSET -> House_color
House_color: FeatureColorSetter
    COLOR = 0,0.666667,1
    FILL_COLOR = 0,0.666667,1
    MODE = Fixed
    COLORED -> House
    COLORED -> Clipper [CLIPPER]
    COLORED -> SpatialFilter_5 [Filter]
    COLORED -> NeighborFinder_2 [CANDIDATE]
    COLORED -> MinDistance [SpatialFilter_Filter]
    COLORED -> MinDistance [NeighborFinder_Candidate]
    COLORED -> MinDistance [SpatialFilter_2_Filter]
    COLORED -> AreaOnAreaOverlayer_3 [AREA]
    COLORED -> HouseIntersection [House]
    COLORED -> Bufferer
House: Inspector

Bookmark: Min: property boundaries
Viakop_313_fast (reader ESRISHAPE_2)
    attributes: MUNICIPALI char(4)
    -> Viakop_313_fast
    -> MinDistance [SpatialFilter_2_Candidate]

Bookmark: Detaljplan (DP_Område) from XML-reader
DP_Omrade (reader XML_1)
    attributes: DP_Omrade.id xml_char(3), minus xml_char(1), minus.href xml_char(6), minus{} xml_char(1), minus{}.href xml_char(6), plus xml_char(1), plus.href xml_char(6), plus{} xml_char(1), plus{}.href xml_char(6), xml_fragment xml_xml, xml_id xml_char(21), xml_matched_element xml_char(10), xml_parent_child_pos xml_char(1), xml_parent_id xml_char(1)
    -> CsmapReprojector
minus (reader XML_1)
    attributes: minus xml_char(1), minus.href xml_char(6), xml_fragment xml_xml, xml_id xml_char(20), xml_matched_element xml_char(6), xml_parent_child_pos xml_decimal(3,0), xml_parent_id xml_char(21)
    -> CsmapReprojector_2
plus (reader XML_1)
    attributes: plus xml_char(1), plus.href xml_char(6), xml_fragment xml_xml, xml_id xml_char(19), xml_matched_element xml_char(5), xml_parent_child_pos xml_decimal(3,0), xml_parent_id xml_char(21)
    -> CsmapReprojector_3

Bookmark: Detaljplan from GML-reader
DP_Grans (reader GML_1)
    attributes: typ{} xml_char(5), linje xml_geometry
    -> CsmapReprojector_4
DP_Planbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean
    -> CsmapReprojector_5
DP_Egenskapsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> CsmapReprojector_6
DP_Plan (reader GML_1)
    attributes: uuid xml_buffer, planid xml_buffer, akt xml_buffer, internAkt xml_buffer, diarienummer{} xml_buffer, ursprungsakt xml_buffer, tillkomst xml_buffer, ursprung xml_char(7), ursprungligPlantyp xml_char(3), konvertering xml_char(10), plantyp xml_char(3), forslag xml_boolean, plannamn xml_buffer, berordPlan{} xml_buffer, berordBestammelse{} xml_buffer, syfte xml_buffer, syftedokumentation xml_buffer, kommun xml_buffer, loggning{}.owns xml_boolean, loggning{}.DP_Logg.datum xml_date, loggning{}.DP_Logg.handelse xml_buffer, loggning{}.DP_Logg.notering xml_buffer, utgava xml_buffer, fysisktArkiv xml_buffer, digitaltArkiv xml_buffer, registreringsdatum xml_date, registerstatus xml_char(1), plananmarkning xml_buffer, hojdsystem xml_buffer, koordinatsystem xml_buffer,
      katalog xml_buffer, katalogversion xml_buffer, planomrade{} xml_geometry, anvandningsbestammelse{}.nilReason xml_buffer, anvandningsbestammelse{}.gml_remoteSchema xml_buffer, anvandningsbestammelse{}.xlink_href xml_buffer, anvandningsbestammelse{}.xlink_title xml_buffer, anvandningsbestammelse{}.owns xml_boolean, generellPlanbestammelse{}.nilReason xml_buffer, generellPlanbestammelse{}.gml_remoteSchema xml_buffer, generellPlanbestammelse{}.xlink_href xml_buffer, generellPlanbestammelse{}.xlink_title xml_buffer, generellPlanbestammelse{}.owns xml_boolean
    -> CsmapReprojector_7
DP_Omrade (reader GML_1)
    attributes: plus.nilReason xml_buffer, plus.gml_remoteSchema xml_buffer, plus.xlink_href xml_buffer, plus.xlink_title xml_buffer, plus.owns xml_boolean, minus.nilReason xml_buffer, minus.gml_remoteSchema xml_buffer, minus.xlink_href xml_buffer, minus.xlink_title xml_buffer, minus.owns xml_boolean
    -> CsmapReprojector_8
DP_Data (reader GML_1)
    attributes: tillampning xml_char(4), beskrivning xml_buffer, grans{}.nilReason xml_buffer, grans{}.gml_remoteSchema xml_buffer, grans{}.xlink_href xml_buffer, grans{}.xlink_title xml_buffer, grans{}.owns xml_boolean, omrade{}.nilReason xml_buffer, omrade{}.gml_remoteSchema xml_buffer, omrade{}.xlink_href xml_buffer, omrade{}.xlink_title xml_buffer, omrade{}.owns xml_boolean, plan{}.owns xml_boolean
    -> CsmapReprojector_9
DP_Anvandningsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, anvandningsslag xml_buffer, precisering xml_buffer, huvudsaklig xml_boolean, egenskapsbestammelse{}.nilReason xml_buffer, egenskapsbestammelse{}.gml_remoteSchema xml_buffer, egenskapsbestammelse{}.xlink_href xml_buffer, egenskapsbestammelse{}.xlink_title xml_buffer, egenskapsbestammelse{}.owns xml_boolean, administrativBestammelse{}.nilReason xml_buffer, administrativBestammelse{}.gml_remoteSchema xml_buffer, administrativBestammelse{}.xlink_href xml_buffer, administrativBestammelse{}.xlink_title xml_buffer, administrativBestammelse{}.owns xml_boolean
    -> CsmapReprojector_10
DP_AdministrativBestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> CsmapReprojector_11

Bookmark: Connects bestämmelser to områden
FeatureMerger_Egenskap
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(ID_join) @Value(omrade.xlink_href) AUTO
    LIST_ATTRS_TO_INCLUDE = beteckning ursprunglig uuid
    LIST_NAME = EgenskapList
    MERGE_TYPE = Attributes Only
    PROCESS_DUPS = Yes
    REJECT_NULL_MISSING_KEYS = No
    SUPPLIERS_FIRST = No
    MERGED -> FeatureMerger_Anvandning [REQUESTOR]
    UNMERGED_REQUESTOR -> FeatureMerger_Anvandning [REQUESTOR]
FeatureMerger_Anvandning
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(ID_join) @Value(omrade.xlink_href) AUTO
    LIST_ATTRS_TO_INCLUDE = beteckning ursprunglig uuid
    LIST_NAME = AnvandningList_beteckning
    MERGE_TYPE = Attributes Only
    PROCESS_DUPS = Yes
    REJECT_NULL_MISSING_KEYS = No
    SUPPLIERS_FIRST = No
    MERGED -> AttributeRemover
    UNMERGED_REQUESTOR -> AttributeRemover

Bookmark: Finds area where buildings are permitted
Tester
    BOOL_OP = OR
    TEST_CLAUSE = TEST @Value(beteckning) = n
    PASSED -> PythonCaller
    PASSED -> Python_in
PythonCaller
    NEW_ATTRIBUTES = ursprunglig_bebyggas
    PYTHONSOURCE:
      import fme
      import fmeobjects
      # Template Function interface:
      # When using this function, make sure its name is set as the value of
      # the 'Class or Function to Process Features' transformer parameter
      def processFeature(feature):
          testString = 'inte bebyggas'
          i = 0
          item = feature.getAttribute('EgenskapList{%i}.ursprunglig' % (i))
          bebyggas = True

          while item:
              i += 1
              if testString in item:
                  bebyggas = False
                  break
              item = feature.getAttribute('EgenskapList{%i}.ursprunglig' % (i))

          feature.setAttribute('ursprunglig_bebyggas', bebyggas)
    PYTHONSYMBOL = processFeature
    -> Tester_Byggbart
    -> Python_Out
Tester_Byggbart
    BOOL_OP = OR
    TEST_CLAUSE = TEST @Value(ursprunglig_bebyggas) = Yes
    PASSED -> PointOnAreaOverlayer [AREA]
Note: To get egenskaper from points
PointOnAreaOverlayer
    ATTR_ACCUM_MODE = Merge Incoming
    ATTR_CONFLICT_RES = Use Original
    CANDIDATE_LIST_ATTRS_TO_INCLUDE = beteckning ursprunglig variabel{}.DP_VarArtal.namn variabel{}.DP_VarArtal.varde variabel{}.DP_VarDatum.namn variabel{}.DP_VarDatum.varde variabel{}.DP_VarDecimaltal.namn variabel{}.DP_VarDecimaltal.varde variabel{}.DP_VarHeltal.namn variabel{}.DP_VarHeltal.varde variabel{}.DP_VarKod.namn variabel{}.DP_VarKod.varde variabel{}.DP_VarLinje.namn variabel{}.DP_VarLinje.varde variabel{}.DP_VarPunkt.namn variabel{}.DP_VarPunkt.varde variabel{}.DP_VarText.namn variabel{}.DP_VarText.varde variabel{}.owns
    CANDIDATE_LIST_ATTRS_TO_INCLUDE_MODE = Selected Attributes
    CANDIDATE_LIST_NAME = egenskap
    DEAGGREGATE_INPUT = Yes
    OV_ATTR = _overlaps
    POLYS_FIRST = NO
    AREA -> PythonCaller_Nockhojd
Note: Finds max nockhöjd / (Other heights not considered)
PythonCaller_Nockhojd
    NEW_ATTRIBUTES = max_nock
    PYTHONSOURCE:
      import fme
      import fmeobjects
      # Template Function interface:
      # When using this function, make sure its name is set as the value of
      # the 'Class or Function to Process Features' transformer parameter
      def processFeature(feature):
          testString = 'gsta nockh'
          i = 0
          item = feature.getAttribute('egenskap{%i}.ursprunglig' % (i))

          while item:
              if testString in item:
                  maxNock = feature.getAttribute('egenskap{%i}.beteckning' % (i))
                  break
              i += 1
              item = feature.getAttribute('egenskap{%i}.ursprunglig' % (i))

          maxNock = maxNock.replace(",",".")
          maxNock = float(maxNock)
          feature.setAttribute('max_nock', maxNock)
    PYTHONSYMBOL = processFeature
    -> PythonCaller_Takvinkel
Note: Finds min and max takvinkel
PythonCaller_Takvinkel
    NEW_ATTRIBUTES = max_takvinkel min_takvinkel
    PYTHONSOURCE:
      import fme
      import fmeobjects
      # Template Function interface:
      # When using this function, make sure its name is set as the value of
      # the 'Class or Function to Process Features' transformer parameter
      def processFeature(feature):
          testString_1 = 'gsta taklutning'
          teststring_2 = 'taklutning i grader'
          i = 0
          item = feature.getAttribute('egenskap{%i}.ursprunglig' % (i))
          maxTakVinkel = False
          minTakVinkel = False

          while item:
              if testString_1 in item:
                  maxTakVinkel = feature.getAttribute('egenskap{%i}.beteckning' % (i))
                  break
              elif teststring_2 in item:
                  varIndex = 0
                  varItem = feature.getAttribute('egenskap{%i}.variabel{%i}.DP_VarDecimaltal.namn' % (i, varIndex))
                  while varItem:
                      if 'minvinkel' in varItem:
                          minTakVinkel = feature.getAttribute('egenskap{%i}.variabel{%i}.DP_VarDecimaltal.varde' % (i, varIndex))
                      elif 'maxvinkel' in varItem:
                          maxTakVinkel = feature.getAttribute('egenskap{%i}.variabel{%i}.DP_VarDecimaltal.varde' % (i, varIndex))
                      varIndex += 1
                      varItem = feature.getAttribute('egenskap{%i}.variabel{%i}.DP_VarDecimaltal.namn' % (i, varIndex))
              i += 1
              item = feature.getAttribute('egenskap{%i}.ursprunglig' % (i))

          if maxTakVinkel:
              #maxTakVinkel = maxTakVinkel.replace(",",".")
              #maxTakVinkel = float(maxTakVinkel)
              feature.setAttribute('max_takvinkel', maxTakVinkel)
          if minTakVinkel:
              feature.setAttribute('min_takvinkel', minTakVinkel)
    PYTHONSYMBOL = processFeature
    -> Extruder
    -> AttributeKeeper_2
AttributeKeeper_2
    KEEP_ATTRS = min_takvinkel,max_nock,max_takvinkel,DP_Omrade.id
    -> FeatureMerger_3 [SUPPLIER]

Bookmark: For 3D and visualisation
  This part is to visualize teh areas that are allowed to build in 3D with the height = max building height.
Extruder [off]
    DIRECTION = Vertical
    DISTANCE = @Value(max_nock)
    EXTRUDED -> AppearanceSetter [GEOMETRY]
AppearanceSetter
    ALPHA = 0.6
    DEF_STORAGE = Create New Definitions
    DIFFUSE_COLOR = 0.647059,0.960784,0.478431
    GQUERY:
      for $geom in //geometry
      where $geom/count(parent::geometry) = 0
      return number($geom/@fme_id)
    SET_ON_SIDE = Front and Back Sides
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> 3D_visualization
3D_visualization: Inspector

Bookmark: Min: Parking availability - step 1: check if house intersects potential parking space
Note: Eliminate extra coordinates
Generalizer_2
    ALG_TEXT = Douglas (Generalize)
    CLEANING_TOLERANCE = None
    PRESERVE = Yes
    PRESERVE_PATHS = Yes
    TOLERANCE = 0.005
    -> AreaGapAndOverlapCleaner
Note: Cleans gaps and overlaps between two layers. Data specific.
AreaGapAndOverlapCleaner
    CLEANING_TOLERANCE = 0.0005
    CONNECT_Z_MODE = First Wins
    DEAGGREGATE_INPUT = YES
    FILL_ALL_GAPS = No
    MEASURE_TYPE = Continuous
    MISSING_VAL_MODE = Compute
    REPAIR_METHOD = Longest Boundary
    REPAIRED -> LineIntersectBuffer [GeometryCoercer_3_Input]
    REMNANTS -> LineIntersectBuffer [GeometryCoercer_3_Input]
LineIntersectBuffer
    Chopper_5_Chopped -> RectangleCreater [RoadLines]
    Chopper_5_Chopped -> HouseIntersection [Roadlines]
    Chopper_5_Untouched -> RectangleCreater [RoadLines]
    Chopper_5_Untouched -> HouseIntersection [Roadlines]
    Clipper_3_Inside -> RectangleCreater [Polygons]

Bookmark: Min: Height & Roof Angle
AreaOnAreaOverlayer
    ACCUM_ATTRS_NAME = Merge Incoming Attributes
    CLEANING_TOLERANCE = None
    CONNECT_Z_MODE = First Wins
    DEAGGREGATE_INPUT = Yes
    OVC_ATTR = _overlaps
    AREA -> AreaOnAreaOverlayer_Area
    AREA -> Tester_4
AreaOnAreaOverlayer_Area: Inspector

Bookmark: Min: Parking availability - step 2: If house intersects with potential parking space, check for available space left
Note: Find the area of intersection between house and buffer
AreaOnAreaOverlayer_3
    ACCUM_ATTRS_NAME = Use Attributes From One Feature
    CLEANING_TOLERANCE = None
    CONNECT_Z_MODE = First Wins
    DEAGGREGATE_INPUT = Yes
    OVC_ATTR = _overlaps
    AREA -> Tester_3
Note: Find the area of intersection between house and buffer
Tester_3
    BOOL_OP = OR
    TEST_CLAUSE = TEST @Value(_overlaps) = 2
    PASSED -> Chopper_2 [off]
    PASSED -> SpatialFilter_4 [Filter] [off]
Note: Retrieve all nodes/points of interection
Chopper_2
    DEAGGREGATE_INPUT = Deaggregate
    MAX_VERTICES = 1
    MODE = By Vertex
    REMNANT_ATTR = _remnant
    CHOPPED -> HouseIntersection [Vertices]

FME custom transformer LineIntersectBuffer

GeometryCoercer_3_Input (input)
    -> GeometryCoercer_3
GeometryCoercer_3
    GQUERY:
      for $geom in //geometry
      where $geom/count(parent::geometry) = 0
      return number($geom/@fme_id)
    KIND = fme_line
    COERCED -> LineOnLineOverlayer [LINE]
Note: Find the linse that intersects between the road and property.
LineOnLineOverlayer
    ATTRS_ACCUM_MODE = Use Attributes From One Feature
    CLEANING_TOLERANCE = None
    DEAGGREGATE_INPUT = Yes
    GENERATE_LIST_DROP = NO
    LOG_LEVEL = Full
    OV_ATTR = _overlaps
    SEPARATE_COLLINEAR_SEGMENTS = No
    LINE -> Tester_4
Note: Find the linse that intersects between the road and property.
Tester_4
    BOOL_OP = OR
    TEST_CLAUSE = TEST @Value(_overlaps) = 2
    PASSED -> Chopper_5
Chopper_5
    DEAGGREGATE_INPUT = Deaggregate
    MAX_VERTICES = 2
    MODE = By Vertex
    REMNANT_ATTR = _remnant
    CHOPPED -> Counter
    UNTOUCHED -> Counter
    UNTOUCHED -> Chopper_5_Untouched (output)
Chopper_5_Untouched (output)
Counter
    CNT_ATTR = UniqueID
    DOMAIN = counter
    SCOPE = Global
    START = 1
    -> Bufferer_3
    -> Chopper_5_Chopped (output)
Chopper_5_Chopped (output)
Note: Create a 5m meter, this is potential parking space.
Bufferer_3
    ANGLE = 22.5
    CAP_STYLE = None
    CORNER_STYLE = Round
    MODE = AREA
    OFFSET = 5
    BUFFERED -> Clipper_3 [CLIPPEE]
Clipper_3_Clipper (input)
    -> Clipper_3 [CLIPPER]
Note: The 5m buffer should only extend to the propety area, not the road.
Clipper_3
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> Clipper_3_Inside (output)
Clipper_3_Inside (output)

FME custom transformer Geohash_2
This transformer will calculate a list of Geohash polygons ("http://en.wikipedia.org/wiki/Geohash") that will approximate the shape of the input polygon. 
The maximum length of the Geohashes ( and thus the resolution) can be set by the user.
The Geohash list is pipe ("|") separated and stored in the attribute "_geohash".

Parameters:
- HASH =   # Maximum Hash Length

BASE (input)
    -> AttributeExposer
Note: Expose input attributes
AttributeExposer
    ATTR_LIST = _id
    -> SpatialFilter [BASE]
    -> SpatialFilter_2 [BASE]
TILES (input)
    -> AttributeExposer_2
Note: Expose input attributes
AttributeExposer_2
    ATTR_LIST = _id,_geometry
    -> StringLengthCalculator
Note: Calculate geohash length
StringLengthCalculator
    LENGTH_ATTR = _length
    SRC_ATTR = _geometry
    -> Tester
Note: If geohash length / meets target, bail out
Tester
    BOOL_OP = OR
    TEST_CLAUSE = TEST @Value(_length) < $(HASH)
    PASSED -> Cloner
    FAILED -> Cloner_2
Note: Create 32 copies of geohash
Cloner
    COPIES = 32
    COPYATT = _copynum
    COPY -> AttributeValueMapper
Note: Convert copy / number to base32
AttributeValueMapper
    DEFAULT_VALUE = KEY
    DIRECTION = Forward (Source To Destination)
    LUT = 10,b,11,c,12,d,13,e,14,f,15,g,16,h,17,j,18,k,19,m,20,n,21,p,22,q,23,r,24,s,25,t,26,u,27,v,28,w,29,x,30,y,31,z
    SRC = _copynum
    VAL_ATTR = _looked_up
    -> StringConcatenator
Note: Add converted copy / number to geohash
StringConcatenator
    PARM_LINE = @Value(_geometry)@Value(_looked_up)
    VAL_ATTR = _geometry
    -> GeometryReplacer
Note: Replace old geometry / from new geohash
GeometryReplacer
    ATTR = _geometry
    KIND_LONG = Geohash
    OUTPUT_POINT_DISPLAY = Area
    -> SpatialFilter [CANDIDATE]
Note: Extract all new polygons / completely within source
SpatialFilter
    BASE_TYPE = Multiple Bases
    CURVE_BOUNDARY_RULE_PARAM = Default Rule
    GROUP_BY = _id
    MERGE_ATTRS = No
    PASS_CRITERIA = Pass Against One Base
    PREDICATES = CONTAINS
    USE_BOUNDING_BOX = No
    PASSED -> AttributeRemover
    FAILED -> SpatialFilter_2 [CANDIDATE]
Note: Clean up attributes
AttributeRemover
    REMOVE_ATTRS = _length,_looked_up
    -> INSIDE (output)
INSIDE (output)
Note: Extract all polygons / intersecting edge
SpatialFilter_2
    BASE_TYPE = Multiple Bases
    CURVE_BOUNDARY_RULE_PARAM = Default Rule
    GROUP_BY = _id
    MERGE_ATTRS = No
    PASS_CRITERIA = Pass Against One Base
    PREDICATES = INTERSECTS
    USE_BOUNDING_BOX = No
    PASSED -> AttributeRemover_2
Note: Placeholder
Cloner_2
    COPIES = 1
    COPYATT = _copynum
    COPY -> AttributeRemover_2
Note: Clean up attributes
AttributeRemover_2
    REMOVE_ATTRS = _length,_looked_up
    -> EDGE (output)
EDGE (output)

FME custom transformer HouseIntersection

Parameters:
- UNIQUEID = @Value(UniqueID)   # UniqueID
- _CLIPPED = @Value(_clipped)   # Clipped
- _COORDCOUNT = @Value(_coordcount)   # Coordcount
- _OVERLAPS = @Value(_overlaps)   # Overlaps
- _PREDICATE = @Value(_predicate)   # Predicate
- _REMNANT = @Value(_remnant)   # Remnant

Vertices (input)
    -> NeighborFinder_3 [BASE]
Roadlines (input)
    -> LineOnAreaOverlayer [LINE]
House (input)
PolygonCutter_Polygons_1 (input)
    -> PolygonCutter [Polygons]
    -> LineOnAreaOverlayer [AREA]
LineOnAreaOverlayer
    ATTR_ACCUM_MODE = Merge Incoming
    ATTR_CONFLICT_RES = Use Original
    CLEANING_TOLERANCE = None
    DEAGGREGATE_INPUT = Yes
    OV_ATTR = _overlaps
    LINE -> NeighborFinder_3 [CANDIDATE]
NeighborFinder_3
    CANDIDATES_FIRST = No
    GROUP_BY = UniqueID
    INSERT_VERTEX = No
    K = 1
    MEASURES_FROM_CANDIDATE = Yes
    MEASURE_TYPE = Continuous
    MODE = Bases and Candidates
    TREAT_POLYGON_AS = Lines
    MATCHED -> VertexCreator
VertexCreator
    MODE_NAME = Add Point
    XVAL = @Value(_closest_candidate_x)
    YVAL = @Value(_closest_candidate_y)
    -> LineExtender
LineExtender
    LEN = 5
    STRETCHED -> PolygonCutter [Lines]
Note: Cutes the big polygon using the perpendicular lines
PolygonCutter
    SNAP_TOLERANCE = 0
    _GROUP_BY = @Value(UniqueID)
    Cut -> PolygonCutter_Cut_1 (output)
PolygonCutter_Cut_1 (output)

FME custom transformer Cal_length

LengthCalculator_2_Input (input)
    -> LengthCalculator_2
Note: Calculate the perimeter of the polygon
LengthCalculator_2
    DIM = 2
    LEN_ATTR = _length
    MULT = 1
    -> AttributeCreator_5
Note: Perimeter -10 /2 is the width of the polygon
AttributeCreator_5
    ATTR_TABLE = SET_TO Width = @Evaluate((@Value(_length)-10)/2)
    -> Tester_13
    -> Tester_12
Note: Width > or = 2.5m becomes green
Tester_13
    BOOL_OP = OR
    TEST_CLAUSE = TEST @Value(Width) >= 2.5
    PASSED -> YesPark_2
Note: Green if area is ok
YesPark_2: FeatureColorSetter
    COLOR = 0,0.666667,0
    FILL_COLOR = 0.631373,1,0.662745
    MODE = Fixed
    COLORED -> Space_for_parking_2
Note: Add message in the attribute table
Space_for_parking_2: AttributeCreator
    ATTR_TABLE = SET_TO Parking = There is space for parking
    -> Yes_Park (output)
Yes_Park (output)
Note: Width < 2.5m becomes red
Tester_12
    BOOL_OP = OR
    TEST_CLAUSE = TEST @Value(Width) < 2.5
    PASSED -> NoPark_3
Note: Red if not ok for parking
NoPark_3: FeatureColorSetter
    COLOR = 0.666667,0,0
    FILL_COLOR = 1,0,0.498039
    MODE = Fixed
    COLORED -> NO_Space_for_parking
Note: Add message in the attribute table
NO_Space_for_parking: AttributeCreator
    ATTR_TABLE = SET_TO Parking = There is no space for parking
    -> No_Park (output)
No_Park (output)

FME custom transformer RectangleCreater

Parameters:
- UNIQUEID = @Value(UniqueID)   # UniqueID

Polygons (input)
    -> VertexExtractor
    -> PolygonCutter_2 [Polygons]
    -> LineOnAreaOverlayer [AREA] [off]
VertexExtractor
    Point -> NeighborFinder [BASE]
    Point -> VertexExtractor_Point
VertexExtractor_Point: Inspector
RoadLines (input)
    -> LineOnAreaOverlayer [LINE] [off]
    -> NeighborFinder [CANDIDATE]
LineOnAreaOverlayer
    ATTR_ACCUM_MODE = Merge Incoming
    ATTR_CONFLICT_RES = Use Original
    CLEANING_TOLERANCE = None
    DEAGGREGATE_INPUT = Yes
    OV_ATTR = _overlaps
    LINE -> NeighborFinder [CANDIDATE] [off]
NeighborFinder
    CANDIDATES_FIRST = No
    GROUP_BY = UniqueID
    INSERT_VERTEX = No
    K = 1
    MEASURES_FROM_CANDIDATE = Yes
    MEASURE_TYPE = Continuous
    MODE = Bases and Candidates
    TREAT_POLYGON_AS = Lines
    MATCHED -> Tester
Tester
    BOOL_OP = OR
    TEST_CLAUSE = TEST @Value(_distance) > 0
    PASSED -> VertexCreator
VertexCreator
    MODE_NAME = Add Point
    XVAL = @Value(_closest_candidate_x)
    YVAL = @Value(_closest_candidate_y)
    -> LineExtender
LineExtender
    LEN = 5.2
    STRETCHED -> PolygonCutter_2 [Lines]
PolygonCutter_2
    SNAP_TOLERANCE = 0
    _GROUP_BY = @Value(UniqueID)
    Cut -> Rectangles (output)
Rectangles (output)

FME custom transformer VertexExtractor
Extracts all vertices from input geometries and outputs them as 3D Points.
When a vertex is 2D Point, its Z value is set to the value which is given as a user parameter. If the Z value is not specified, 2D points will be returned.
Input Ports
Input is the data containing coordinates that you would like to turn into vertices. If the source feature is a donut polygon or an aggregate, then this transformer will decompose the feature into its components before breaking them up.
Additionally all point features receive the attributes _feature_number and _vertex_number which, in combination, are unique for every source feature and, respectively, its parts.
The _part_number indicates whether the resulting point was derived from a donut polygon or an aggregate. If a donut or an aggregate was the origin, the _part_number is 0 for the first part and 1 or greater for all other parts. The _part_number is 0 in case of simple features.
Note: If you don't need to know the part numbers, you can also use the Chopper transformer which comes with FME. Setting Maximum Vertices to 1 in the Chopper exposes feature vertices. 
    Output Ports
Output is the point(s) that were created from the transformer. Each resulting point inherits all attributes from its source feature.
    Parameters
When a vertex is 2D Point, its Z value is set to the value which is given as a user parameter. If the Z value is not specified, 2D points will be returned.

Parameters:
- DEFAULT_Z_VALUE =   # Z Value for 2D Point (optional)

Input (input)
    -> Deaggregator
Note: If input feature consists of aggregates, / split it into "simple" features
Deaggregator
    ATTR_ACCUM_MODE = Merge List Attributes
    ATTR_CONFLICT_RES = Use List Attribute Values
    EXPLODE_INSTANCES = No
    LIST_ATTR_MODE_LOOKUP = LEAN
    MODE = Flatten One Level
    PART_NUMBER_FIELD = _part_number
    SPLIT_COMPOSITES = Yes
    DEAGGREGATED -> Counter
Counter
    CNT_ATTR = _feature_number
    DOMAIN = counter
    SCOPE = Local
    START = 0
    -> CoordinateConcatenator
Note: Get concatenated coordinates string
CoordinateConcatenator
    COORDINATES_TO_INCLUDE_DIS = X Y Z
    COORD_ATTR = _coordinates
    COORD_DELIM = \
    ELEMENT_DELIM = ,
    PRECISION = Yes
    -> AttributeSplitter
Note: Split the concatenated coordinates string / to each coordinate and make a list of those
AttributeSplitter
    ATTR_NAME = _coordinates
    DELIMITER = \
    DROP_EMPTY_PARTS = No
    LIST_NAME = _coordinate
    TRIM_OPTION = Both
    -> DimensionExtractor
Note: Extracts dimension, 3 or 2
DimensionExtractor
    DIM_ATTR = _dimension
    -> GeometryRemover
Note: Remove all geometries to prevent / creating many copies of geometry objects / before exploding the coordinate list. / this is very important for the memory usage efficiency.
GeometryRemover
    -> ListExploder
Note: Explode the coordinate list / into every vertex coordinate
ListExploder
    ATTR_ACCUM_MODE = Merge Incoming List
    ATTR_CONFLICT_RES = Use Incoming List
    INDEX_ATTR = _element_index
    LIST_ATTR = _coordinate{}
    ELEMENTS -> AttributeSplitter_1
Note: Change each vertex coordinate / to list structure containing [x,y,(z)]
AttributeSplitter_1
    ATTR_NAME = _coordinate
    DELIMITER = ,
    DROP_EMPTY_PARTS = No
    LIST_NAME = _list
    TRIM_OPTION = Both
    -> TestFilter
Note: Divide the work flow according to the dimension / and expose the list elements i.e. x,y.(z)
TestFilter
    DEFAULT_VALUE = <UNFILTERED>
    TEST_LIST = TEST_CLAUSE,"TEST @Value(_dimension) = 3",TEST_LIST,"&_dimension,=,3",TEST_MODE,Automatic,BOOL_OP,OR,_dimension = 3,TEST_CLAUSE,"TEST @Value(_dimension) = 2",TEST_LIST,"&_dimension,=,2",TEST_MODE,Automatic,BOOL_OP,OR,_dimension = 2
    _dimension = 3 -> AttributeManager
    _dimension = 2 -> ParameterFetcher
Note: When the dimension is 2 and default z is set, / set default value to _list{2} i.e. z. / the default value is given as a parameter
ParameterFetcher
    ATTR_LIST = _list{2} {$(DEFAULT_Z_VALUE)}
    -> AttributeManager
AttributeManager
    ATTR_TABLE:
      REMOVE _dimension
      RENAME_SET_VALUE _element_index > _vertex_number
      RENAME_SET_VALUE _list{2} > _z
      RENAME_SET_VALUE _list{1} > _y
      RENAME_SET_VALUE _list{0} > _x
      REMOVE _coordinate
      REMOVE _coordinates
      REMOVE _list{}
    -> VertexCreator
Note: Finally, create point from x,y,z
VertexCreator
    MODE_NAME = Replace with Point
    XVAL = @Value(_x)
    YVAL = @Value(_y)
    ZVAL = @Value(_z)
    -> Point (output)
Point (output)

FME custom transformer MinDistance

Parameters:
- MIN_DIST = @Value(min_dist)   # Min Dist

SpatialFilter_Filter (input)
    -> SpatialFilter [Filter]
SpatialFilter_Candidate (input)
    -> SpatialFilter [Candidate]
Note: Checks if house is in an area where buildings are allowed
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN
    USE_BOUNDING_BOX = No
    PASSED -> SpatialFilter_3 [Filter]
NeighborFinder_Candidate (input)
    -> NeighborFinder [CANDIDATE]
SpatialFilter_2_Filter (input)
    -> SpatialFilter_2 [Filter]
SpatialFilter_2_Candidate (input)
    -> SpatialFilter_2 [Candidate]
Note: Checks if house is inside property boundaries (no overlaps)
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN
    USE_BOUNDING_BOX = No
    PASSED -> SpatialFilter_3 [Candidate]
Note: Check if both conditions are met. If yes, then proceed to check minimum distance.
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Generalizer
Note: Eliminate extra points
Generalizer
    ALG_TEXT = Douglas (Generalize)
    PRESERVE = No
    PRESERVE_PATHS = No
    TOLERANCE = 0.005
    -> NeighborFinder [BASE]
    -> SpatialFilter3 (output)
SpatialFilter3 (output)
Note: Checks minimum distance to boundaries
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> Tester_2
Note: Test minimum distance requirement with actual measured minimum distance.
Tester_2
    BOOL_OP = OR
    TEST_CLAUSE = TEST @Value(min_dist) < @Value(_distance)
    PASSED -> Tester_2_Passed (output)
    FAILED -> Tester_2_Failed (output)
Tester_2_Passed (output)
Tester_2_Failed (output)

FME custom transformer PolygonCutter
Cut polygons by lines. 
The input asks for polygons (areas and ellipses are excepted) and lines (lines and arcs are excepted). The polygons are cut and the original attributes are added to the cut polygons. 
There is a group by option in the parameters and vertices can be snapped using the Snapping Tolerance parameter. 
The transformer does not take overlapping areas into account. If areas are overlapping they will be cut into pieces. 
Version 2:
Added the export of unused lines through the unused port. These lines have the attribute _remnant added and is set to 'yes' if it intersects with an area and 'no' if not. Non-line features will not have the attribute.
Author:     lars de vries 
Company:        Omkeere
Phone:      +31 (0)6 - 191.777.82
E-mail:     larsdevries@omkeere.com
Website:        http://omkeere.com
DevVersion: 2017.0.1.0 (build 17288)

Parameters:
- SNAP_TOLERANCE = 0.001   # Snapping Tolerance
- _GROUP_BY =   # Group By

Polygons_-__SpatialRelator_Supplier: Junction
    -> Polygons_-__SpatialRelator_Supplier_Output_-__SpatialRelator_Supplier
Polygons_-__SpatialRelator_Supplier_Output_-__SpatialRelator_Supplier: Junction
    -> SpatialRelator [Supplier]
    -> Polygons_-__SpatialRelator_Supplier_Output_-__SpatialRelator_Supplier_Output_-__Matcher
Note: ///2017-07-07 LVR / Nog te ontwikkelen: / - Opties voor 3D: Voorkeur voor lijnen of vlakken / - Juiste wijze voor groeperen opnemen
Polygons_-__SpatialRelator_Supplier_Output_-__SpatialRelator_Supplier_Output_-__Matcher: Junction
    -> ChangeDetector [ORIGINAL]
gfPolygonFilter__UNFILTERED__-__MessageLogger_INPUT: Junction
    -> MessageLogger

Bookmark: R1 - Read features
Note: Get _group_by attribute for application in: / - LineBuilder / - Intersector / - AreaBuilder / - SpatialRelator / - Matcher
Polygons (input)
    -> gfPolygonFilter
    -> Polygons_-__SpatialRelator_Supplier
Lines (input)
    -> gfLineFilter

Bookmark: 01 - Filter lines and join if possible
Note: Check the geometry for being a polygon
gfPolygonFilter: GeometryFilter
    BREAK_AGG = No
    GEOM_PORT_NAMES = Area Ellipse
    AREA -> Intersector
    ELLIPSE -> Intersector
    <UNFILTERED> -> gfPolygonFilter__UNFILTERED__-__MessageLogger_INPUT
Note: Check the geometry for being a polygon
gfLineFilter: GeometryFilter
    BREAK_AGG = No
    GEOM_PORT_NAMES = Line Arc
    LINE -> Intersector
    ARC -> Intersector
    <UNFILTERED> -> gfPolygonFilter__UNFILTERED__-__MessageLogger_INPUT

Bookmark: 02 - Cut areas with lines
Note: Intersect all lines by _group_by
Intersector
    ATTRS_ACCUM_MODE = Use Attributes From One Feature
    DEAGGREGATE_INPUT = Yes
    DUPLICATE_Z_NODES = No
    GENERATE_LIST_DROP = NO
    GRP_BY = _group_by
    MEASURE_TYPE = Continuous
    OV_ATTR = _overlaps
    PERFORM_SELF_INTERSECTION = No
    SEG_ATTR = _segments
    SEPARATE_COLLINEAR_SEGMENTS = No
    INTERSECTED -> AreaBuilder
Note: Build new areas from intersected lines by _group_by
AreaBuilder
    ALLOW_CYCLES = No
    CHECK_CURVE_DIRECTION = No
    CONNECT_Z_MODE = First Wins
    CONSIDER_NODE_ELEVATION = no
    DONUT_CREATION = YES
    DROP_HOLES = No
    GROUP_BY = _group_by
    LINES_AS_SEGMENTS = No
    POLY_ACCUM_ATTRS_NAME = Use Attributes From One Feature
    SNAPTYPE_PARAM = Vertex Snapping
    SNAP_TOLERANCE = $(SNAP_TOLERANCE)
    AREA -> SpatialRelator [Requestor]
    AREA -> SpatialFilter [Filter]
    Incomplete -> SpatialFilter [Candidate]

Bookmark: 03 - Post proces properties
Note: Relate original attributes for areas that are contained within their original shape
SpatialRelator
    AGGREGATE_HANDLING = No
    ATTR_ACCUM_MODE = Only Use Supplier
    CALC_CARD = No
    CURVE_BOUNDARY_RULE_PARAM = Default Rule
    GROUP_BY = _group_by
    PREDICATES = WITHIN
    SUCCESS_ATTR = _related_candidates
    -> ChangeDetector [REVISED]
Note: Check features for changes
ChangeDetector
    BLANK_AND_MISSING_DIFFER = No
    LENIENT_MATCH = No
    MATCH = 2D
    MATCHATTRS = _group_by
    MATCH_STRATEGY = Match Selected Attributes
    UNCHANGED -> AttributeRemover
    ADDED -> AttributeRemover_2

Bookmark: 04.1 - Attribute cleaning
Note: Remove intermediate attributes
AttributeRemover
    REMOVE_ATTRS = _group_by,_related_candidates
    -> Untouched (output)
AttributeRemover_2
    REMOVE_ATTRS = _group_by,_related_candidates
    -> Cut (output)

Bookmark: W2 - Output features
  Output features through the Untouched port if features are identical as the input and through the Cut port if they are cut into smaller pieces
Untouched (output)
Cut (output)

Bookmark: 04 - Check unused lines for remnants
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator
    FAILED -> AttributeCreator_2
AttributeCreator
    ATTR_TABLE = SET_TO _remnant = yes
    -> AttributeCreator_2_OUTPUT_-__Unused
AttributeCreator_2
    ATTR_TABLE = SET_TO _remnant = no
    -> AttributeCreator_2_OUTPUT_-__Unused
AttributeCreator_2_OUTPUT_-__Unused: Junction
    -> Unused (output)

Bookmark: W1 - Incorrect geometry
  Log and output unexpected geometries as Unused.
MessageLogger
    LOGFEATS = Yes
    MAXCOORDS = 5
    MAXFEATS = 20
    MESSAGE = Geometries do not contain the expected geometry. Make sure that the same geometry in fed as the name of the input port. Result my not be as aspected
    TYPE = WARN
    -> Unused (output)
Unused (output)
