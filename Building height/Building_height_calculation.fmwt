FME workspace Building_height_calculation.fmwt
Title: Building_height_calculation

Parameters:
- SourceDataset_IFC = $(FME_MF_DIR)2/House 45/180430 - House 45.ifc   # Source Industry Foundation Class (IFC) File(s)
- SourceDataset_XML = $(FME_MF_DIR)2/Masterskript/ArildCentral.xml   # Source XML File(s)
- SourceDataset_GML = $(FME_MF_DIR)2/Masterskript/ArildCentral.xml   # Source Geography Markup Language (GML) File(s)
- SourceDataset_GEOTIFF = $(FME_MF_DIR)1/Skript från Per-Ola/DEM_Arild_2.tif   # Source GeoTIFF File(s)
- zOffset2 = 20   # " " Attribute Value
- DEM_resolution = 2   # DEM resolution

Readers:
- IFC_1: IFC from $(SourceDataset_IFC)
- XML_1: XML from $(SourceDataset_XML)
- GML_1: GML from $(SourceDataset_GML)
- GEOTIFF_1: GEOTIFF from $(SourceDataset_GEOTIFF)

Note: FeatureColorSetter_prickadMark : Colored
Junction_15
    -> FeatureColorSetter_prickadMark_Colored
FeatureColorSetter_prickadMark_Colored: Inspector
Note: FeatureColorSetter_korsMark : Colored
Junction_17
    -> FeatureColorSetter_korsMark_Colored
FeatureColorSetter_korsMark_Colored: Inspector
Note: FeatureColorSetter_Gata_gang : Colored
Junction_19
    -> FeatureColorSetter_Gata_gang_Colored
FeatureColorSetter_Gata_gang_Colored: Inspector
Note: FeatureColorSetter_Vatten : Colored
Junction_21
    -> FeatureColorSetter_Vatten_Colored
FeatureColorSetter_Vatten_Colored: Inspector
Note: FeatureColorSetter_OtherAreas : Colored
Junction_23
    -> FeatureColorSetter_OtherAreas_Colored
FeatureColorSetter_OtherAreas_Colored: Inspector
DetailedPlan_draped: Inspector
2DForcer_buildingImport_2D_-__BuildingHeightCheckerNew_2DForcer_buildingImport: Junction
    -> BuildingHeightCheckerNew [2DForcer_buildingImport]
    -> BuildingHeightCheckerNew [2DForcer_buildingImport_2]

Bookmark: XML Reader
plus (reader XML_1)
    attributes: plus xml_char(1), plus.href xml_char(6), xml_fragment xml_xml, xml_id xml_char(19), xml_matched_element xml_char(5), xml_parent_child_pos xml_decimal(3,0), xml_parent_id xml_char(21)
    -> detaljPlanReader [Aggregator_Input]
minus (reader XML_1)
    attributes: minus xml_char(1), minus.href xml_char(6), xml_fragment xml_xml, xml_id xml_char(20), xml_matched_element xml_char(6), xml_parent_child_pos xml_decimal(3,0), xml_parent_id xml_char(21)
    -> detaljPlanReader [Aggregator_Input]
DP_Omrade (reader XML_1)
    attributes: DP_Omrade.id xml_char(3), minus xml_char(1), minus.href xml_char(6), minus{} xml_char(1), minus{}.href xml_char(6), plus xml_char(1), plus.href xml_char(6), plus{} xml_char(1), plus{}.href xml_char(6), xml_fragment xml_xml, xml_id xml_char(21), xml_matched_element xml_char(10), xml_parent_child_pos xml_char(1), xml_parent_id xml_char(1)
    -> detaljPlanReader [FeatureMerger_Supplier]

Bookmark: GML Reader
DP_Grans (reader GML_1)
    attributes: typ{} xml_char(5), linje xml_geometry
    -> detaljPlanReader [AttributeCreator_2_Input]
DP_Omrade (reader GML_1)
    attributes: plus.nilReason xml_buffer, plus.gml_remoteSchema xml_buffer, plus.xlink_href xml_buffer, plus.xlink_title xml_buffer, plus.owns xml_boolean, minus.nilReason xml_buffer, minus.gml_remoteSchema xml_buffer, minus.xlink_href xml_buffer, minus.xlink_title xml_buffer, minus.owns xml_boolean
    -> detaljPlanReader [FeatureMerger_Requestor]
DP_Egenskapsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> detaljPlanReader [PythonCaller_Byggnadshojd_Input]
DP_Anvandningsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, anvandningsslag xml_buffer, precisering xml_buffer, huvudsaklig xml_boolean, egenskapsbestammelse{}.nilReason xml_buffer, egenskapsbestammelse{}.gml_remoteSchema xml_buffer, egenskapsbestammelse{}.xlink_href xml_buffer, egenskapsbestammelse{}.xlink_title xml_buffer, egenskapsbestammelse{}.owns xml_boolean, administrativBestammelse{}.nilReason xml_buffer, administrativBestammelse{}.gml_remoteSchema xml_buffer, administrativBestammelse{}.xlink_href xml_buffer, administrativBestammelse{}.xlink_title xml_buffer, administrativBestammelse{}.owns xml_boolean
    -> detaljPlanReader [FeatureMerger_Anvandning_Supplier]

Bookmark: Detailed development plan
  Read and modify the detailed development plan
Note: Detaljplan / Detailed development plan / Källa: Höganäs kommun, Stadsbyggnadskontoret / Source: Höganäs municipality, Urban planning office
detaljPlanReader
    DP_OMRADE.ID = @Value(DP_Omrade.id)
    XML_PARENT_ID = @Value(xml_parent_id)
    UUID = @Value(uuid)
    MINUS.HREF = @Value(minus.href)
    BESTAMMELSETYP = @Value(bestammelsetyp)
    BETECKNING = @Value(beteckning)
    ANVANDNINGSSLAG = @Value(anvandningsslag)
    GML_ID = @Value(gml_id)
    OMRADE.XLINK_HREF = @Value(omrade.xlink_href)
    PLUS.HREF = @Value(plus.href)
    XML_ID = @Value(xml_id)
    URSPRUNGLIG = @Value(ursprunglig)
    XML_PARENT_CHILD_POS = @Value(xml_parent_child_pos)
    TestFilter_2_prickMark -> FeatureColorSetter_prickadMark
    TestFilter_2_korsMark -> FeatureColorSetter_korsMark
    TestFilter_Gata -> detaljPlanReader_TestFilter_Cykel_-__detaljPlanReader_TestFilter_Cykel
    TestFilter_Gång -> detaljPlanReader_TestFilter_Cykel_-__detaljPlanReader_TestFilter_Cykel
    TestFilter_Cykel -> detaljPlanReader_TestFilter_Cykel_-__detaljPlanReader_TestFilter_Cykel
    TestFilter_Vatten -> FeatureColorSetter_Vatten
    TestFilter__Unfiltered_ -> FeatureColorSetter_OtherAreas
Junction_14
    -> Junction_15
Junction_16
    -> Junction_17
detaljPlanReader_TestFilter_Cykel_-__detaljPlanReader_TestFilter_Cykel: Junction
    -> FeatureColorSetter_Gata_gang
    -> detaljPlanReader_TestFilter_Cykel_-__detaljPlanReader_TestFilter_Cykel_Output_-__Clipper_CLIPPER
Junction_18
    -> Junction_19
Note: mainWallFinder : Intersector_Input
Junction_9
    -> Junction_10
detaljPlanReader_TestFilter_Cykel_-__detaljPlanReader_TestFilter_Cykel_Output_-__Clipper_CLIPPER: Junction
    -> Clipper [CLIPPER]
    -> Junction_11
Junction_20
    -> Junction_21
Junction_22
    -> Junction_23
Note: Removing the area / covering the entire / plan
Tester_EntirePlan
    TEST_MODE = Automatic
    TEST_DESCRIPTION = ""
    TEST_CLAUSE = TEST @Value(ID_join) != #a
    BOOL_OP = OR
    PASSED -> Clipper [CLIPPEE]
    PASSED -> Junction_11
    PASSED -> Tester_EntirePlan_Passed
Tester_EntirePlan_Passed: Inspector
Note: Build_Height_Developmentplan : Input
Junction_11
    -> Junction_12

Bookmark: Set area color for visualization
FeatureColorSetter_prickadMark
    FILL_COLOR = 1,0.14902,0.160784
    MODE = Fixed
    COLOR = 0,0,0
    COLORED -> FeatureColorSetter_prickadMark_COLORED_-__Junction_10
    COLORED -> detaljPlanReader_TestFilter_Cykel_-__detaljPlanReader_TestFilter_Cykel_Output_-__Clipper_CLIPPER
    COLORED -> Junction_14
FeatureColorSetter_korsMark
    FILL_COLOR = 0.423529,0.0627451,0.0666667
    MODE = Fixed
    COLOR = 0,0,0
    COLORED -> FeatureColorSetter_prickadMark_COLORED_-__Junction_10
    COLORED -> detaljPlanReader_TestFilter_Cykel_-__detaljPlanReader_TestFilter_Cykel_Output_-__Clipper_CLIPPER
    COLORED -> Junction_16
FeatureColorSetter_Gata_gang
    FILL_COLOR = 0.666667,0.556863,0.552941
    MODE = Fixed
    COLOR = 0.666667,0.556863,0.552941
    COLORED -> FeatureColorSetter_prickadMark_COLORED_-__Junction_10
    COLORED -> Junction_18
    COLORED -> Junction_9
FeatureColorSetter_Vatten
    FILL_COLOR = 0,0,1
    MODE = Fixed
    COLOR = 0,0,1
    COLORED -> Junction_20
FeatureColorSetter_OtherAreas
    FILL_COLOR = 0.666667,1,0.498039
    MODE = Fixed
    COLOR = 0,0,0
    COLORED -> Tester_EntirePlan
    COLORED -> Junction_22

Bookmark: Draping detailed development plan on DEM for visualization
FeatureColorSetter_prickadMark_COLORED_-__Junction_10: Junction
    -> SurfaceDraper [DRAPE_FEATURES]
Note: TINGenerator_DEM : Triangles
Junction_3
    -> SurfaceDraper [POINTS/LINES]
SurfaceDraper
    TOLERANCE = 1
    DRAPE_TYPE = VERTEX
    INTERPOLATION_TYPE = AUTO
    ADDZ_TYPE = Replace Z
    DRAPED_FEATURES -> DetailedPlan_draped

Bookmark: "Transforming" the building
  "Transforming" (=translate and rotate) the building. The building is a surface model that is transformed from IFC-model to GIS (surface model).
Note: FeatureColorSetter_Gata_gang : Colored
Junction_10
    -> mainWallFinder [Intersector_Input]
AttributeCreator_Offset
    ATTR_TABLE = SET_TO zOffset = $(zOffset2)
    -> Offsetter_2
Offsetter_2
    YOFF = 6239396
    XOFF = 92770
    ZOFF = @Value(zOffset)
    MODE = Cartesian Coordinate
    OFFSET -> Rotator
Rotator
    YORIG = 6239396
    ANGLE = 156
    XORIG = 92770
    ROTATED -> importedBuilding
    ROTATED -> TestFilter
importedBuilding: Inspector
TestFilter
    DEFAULT_VALUE = <UNFILTERED>
    TEST_LIST = BOOL_OP,OR,COMPOSITE_TEST,<Unused>,TEST_CLAUSE,"TEST @Value(type) = mainWalls",mainWalls
    mainWalls -> 2DForcer_buildingImport
    mainWalls -> mainWallFinder [inputWalls]
2DForcer_buildingImport
    2D -> 2DForcer_buildingImport_2D_-__BuildingHeightCheckerNew_2DForcer_buildingImport
Note: Find the main wall according to current regualtions, / i.e. the wall with teh greatest visual impact to / the public. Identified as the wall closets to public / street(car, bike, pedestrian)
mainWallFinder
    WALLORDERID = @Value(wallOrderID)
    WALLHEIGHTNEW = @Value(wallHeightNEW)
    WALLHEIGHTOLD = @Value(wallHeightOLD)
    mainWallFinder_Output -> mainWallFinder_mainWallFinder_Output_-__BuildingHeightCheckerCurrent_mainWallFinder

Bookmark: Clipping overlapping areas for visualtisation.
  The area covering the entire plan is clipped where it overlaps other areas. Purely for visualisation.
Clipper
    MISSING_VAL_MODE = Compute
    DEFAULT_VAL = 0
    ATTR_CONFLICT_RES = Use Clippee
    ATTR_ACCUM_MODE = Merge Clipper
    CLIP_TYPE = Multiple Clippers
    CONNECT_Z_MODE = First Wins
    VAL_SOURCE = Clippee Only
    CREATE_AGGREGATES = Yes
    CLIPPED_ATTR = _clipped
    BOUNDARY_CASES = Treat as Inside
    MEASURE_TYPE = Continuous
    LINES_AS_SEGMENTS = No
    PRESERVE_CLIPPEE_EXTENTS = No
    OUTSIDE -> SurfaceDraper [DRAPE_FEATURES]

Bookmark: Building height calculation
Note: Junction_5 : Output
Junction_12
    -> BuildingHeightCheckerCurrent [DevelopmentPlan_Input]
    -> BuildingHeightCheckerNew [DevelopmentPlan_Input]
Note: RasterCellCoercer_DEM : Output
Junction_8
    -> RasterCellCoercer_DEM_OUTPUT_-__BuildingHeightCheckerNew_from_DEM_2
RasterCellCoercer_DEM_OUTPUT_-__BuildingHeightCheckerNew_from_DEM_2: Junction
    -> BuildingHeightCheckerNew [from_DEM_2]
    -> BuildingHeightCheckerNew [from_DEM]
    -> BuildingHeightCheckerCurrent [from_DEM_2]
    -> BuildingHeightCheckerCurrent [from_DEM]
Note: Checking building height according to the "new" method, / i.e. the highest facade of the building is used to derive / building height regardless of orientation. / NB!!! / Connect 2DForcer_buildingImport to both: / 2DForcer_buildingImport and / 2DForcer_buildingImport_2 / Connect RasterCellCoercer_DEM to both: / from_DEM_2 and / from_DEM
BuildingHeightCheckerNew
    maxHeight_if_too_high -> BuildingHeightCheckerNew_maxHeight_if_too_high
    groundElevation -> BuildingHeightCheckerNew_groundElevation
BuildingHeightCheckerNew_maxHeight_if_too_high: Inspector
BuildingHeightCheckerNew_groundElevation: Inspector
Note: Checking building height according to the "new" method, / i.e. the highest facade of the building is used to derive / building height regardless of orientation. / NB!!! / mainWallFinder to both: / 2DForcer_buildingImport and / 2DForcer_buildingImport_2 / Connect RasterCellCoercer_DEM to both: / from_DEM_2 and / from_DEM
BuildingHeightCheckerCurrent
    maxHeight_if_too_high -> BuildingHeightCheckerCurrent_maxHeight_if_too_high
    groundElevation -> BuildingHeightCheckerCurrent_groundElevation
Note: Plane showing max height if building too high.
BuildingHeightCheckerCurrent_maxHeight_if_too_high: Inspector
Note: Plane showing mean ground elevation.
BuildingHeightCheckerCurrent_groundElevation: Inspector

Bookmark: DEM reader
  Do not have DEM for the area that ArildCentral.xml regulates, yet.
GEOTIFF (reader GEOTIFF_1)
    -> RasterCellCoercer_DEM

Bookmark: DEM - digital elevation model
  Importing and preparing DEM. The DEM is used to find the mean ground elevation where the building is placed.
Note: To find building height.
RasterCellCoercer_DEM
    EXTRACT_NODATA = No
    CELL_GEOMETRY = Points
    PRESERVE_ATTRIBUTES = No
    EXTRACT_BAND_VALUES_AS = Z Values
    -> TINGenerator_DEM [POINTS/LINES]
    -> Junction_7
Note: For draping planning map.
TINGenerator_DEM
    TOLERANCE = 0.01
    TRIANGLES -> Junction
Note: SurfaceDraper : Points/Lines
Junction
    -> Junction_3
Note: BuildingHeightCheckerNew_from_DEM_2 : Input
Junction_7
    -> Junction_8

Bookmark: IFC Reader
IfcRoof (reader IFC_1)
    attributes: GlobalId char(22), Name string, Description string, ObjectType string, Tag string, ShapeType enumeration, Axis geometry, Body geometry, Box geometry, FootPrint geometry
    -> IFC2CityGML_Geometryconverter_parts_Roof [GeometryPartExtractor_2_Input]
IfcSlab (reader IFC_1)
    attributes: GlobalId char(22), Name string, Description string, ObjectType string, Tag string, PredefinedType enumeration, Axis geometry, Body geometry, Box geometry, FootPrint geometry
    -> Junction_2
IfcWallStandardCase (reader IFC_1)
    attributes: GlobalId char(22), Name string, Description string, ObjectType string, Tag string, Axis geometry, Body geometry, Box geometry, FootPrint geometry
    -> IFC2CityGML_Geometryconverter_parts_Walls [GeometryPartExtractor_2_Input]
IfcWindow (reader IFC_1)
    attributes: GlobalId char(22), Name string, Description string, ObjectType string, Tag string, OverallHeight real, OverallWidth real, Axis geometry, Body geometry, Box geometry, FootPrint geometry
    -> IFC2CityGML_Geometryconverter_parts_Window [GeometryPartExtractor_2_Input]
IfcDoor (reader IFC_1)
    attributes: GlobalId char(22), Name string, Description string, ObjectType string, Tag string, OverallHeight real, OverallWidth real, Axis geometry, Body geometry, Box geometry, FootPrint geometry
    -> IFC2CityGML_Geometryconverter_parts_Door [GeometryPartExtractor_2_Input]

Bookmark: Create Surface model
IFC2CityGML_Geometryconverter_parts_Roof
    -> NormalVectorFinder_2 [CoordinateExtractor_Input]
NormalVectorFinder_2
    NormVec_Output -> Ifc2surfacesParts [NormalVectorFinder_Roof_CoordinateExtractor_Input]
Note: IfcSlab
Junction_2
    -> Ifc2surfacesParts [IntersectionLineCreatetor_SurfaceFootprintReplacer_Input_1]
IFC2CityGML_Geometryconverter_parts_Walls
    -> NormalVectorFinder_3 [CoordinateExtractor_Input]
NormalVectorFinder_3
    NormVec_Output -> Ifc2surfacesParts [NormalVectorFinder_Walls_CoordinateExtractor_Input]
IFC2CityGML_Geometryconverter_parts_Window
    -> NormalVectorFinder [CoordinateExtractor_Input]
NormalVectorFinder
    NormVec_Output -> Ifc2surfacesParts [NormalVectorFinder_2_CoordinateExtractor_Input]
IFC2CityGML_Geometryconverter_parts_Door
    -> Ifc2surfacesParts [BinaryEncoder_Door_Input]
Ifc2surfacesParts
    _VZ = @Value(_vz)
    IFC_UNIQUE_ID = @Value(ifc_unique_id)
    GML_PARENT_ID = @Value(ifc_parent_unique_id)
    IFC_PARENT_UNIQUE_ID = @Value(ifc_parent_unique_id)
    AttributeKeeper_6_Output -> AttributeCreator_Offset

Bookmark: Building model
mainWallFinder_mainWallFinder_Output_-__BuildingHeightCheckerCurrent_mainWallFinder: Junction
    -> BuildingHeightCheckerCurrent [mainWallFinder]
    -> BuildingHeightCheckerCurrent [mainWallFinder_2]

FME custom transformer LineDirectionChanger

Parameters:
- _VY = @Value(_vy)   # Vy
- _X_END_WALL = @Value(_x_end_wall)   # X End Wall
- _X_START_WALL = @Value(_x_start_wall)   # X Start Wall
- _VX = @Value(_vx)   # Vx
- _Y_END_WALL = @Value(_y_end_wall)   # Y End Wall
- _Y_START_WALL = @Value(_y_start_wall)   # Y Start Wall

AttributeCreator_2_Input (input)
    -> AttributeCreator_2
AttributeCreator_2
    ATTR_TABLE:
      SET_TO x_norm = @Evaluate(@Value(_y_start_wall)-@Value(_y_end_wall))
      SET_TO y_norm = @Evaluate(@Value(_x_end_wall)-@Value(_x_start_wall))
    -> AttributeCreator_3
AttributeCreator_3
    ATTR_TABLE:
      SET_TO dir_change_x = @Evaluate(@Value(x_norm)*@Value(_vx))
      SET_TO dir_change_y = @Evaluate(@Value(y_norm)*@Value(_vy))
    -> TestFilter_2
TestFilter_2
    DEFAULT_VALUE = <UNFILTERED>
    TEST_LIST:
      BOOL_OP,OR,COMPOSITE_TEST,<Unused>,TEST_CLAUSE,"TEST @Value(dir_change_x) < 0
      TEST @Value(dir_change_y) < 0",change_direction
    change_direction -> Orientor
    <UNFILTERED> -> AttributeRenamer
Orientor
    KIND = REVERSE
    FLIP_APPEARANCES_CHOICE = Yes
    ORIENTED -> AttributeCreator
Note: Reversing also attributes
AttributeCreator
    ATTR_TABLE:
      SET_TO _start_x = @Value(_x_end_wall)
      SET_TO _end_x = @Value(_x_start_wall)
      SET_TO _start_y = @Value(_y_end_wall)
      SET_TO _end_y = @Value(_y_start_wall)
    -> AttributeRemover_3
Note: Need to rename start and end attributes. / For reversed lines these are handled by the / AttributeCreator after the Orientor
AttributeRenamer
    ATTR_TABLE:
      RENAME_SET_DEFAULT _x_start_wall > _start_x
      RENAME_SET_DEFAULT _y_start_wall > _start_y
      RENAME_SET_DEFAULT _x_end_wall > _end_x
      RENAME_SET_DEFAULT _y_end_wall > _end_y
    -> AttributeRemover_3
AttributeRemover_3
    REMOVE_ATTRS = Name,_y_end_wall,ifc_unique_id,_z_end_wall,_z_start_wall,Description,_x_start_wall,ObjectType,_y_start_wall,Tag,_x_end_wall,y_norm,x_norm,ifc_parent_id,ifc_parent_unique_id
    -> AttributeRemover_3_Output (output)
AttributeRemover_3_Output (output)

FME custom transformer WallsTo2D_Python

SurfaceFootprintReplacer_3_Input (input)
    -> SurfaceFootprintReplacer_3
Note: To get 2D. / Gives a geometry (IFMELine) that is easier to handle / later compared to 2DForcer.
SurfaceFootprintReplacer_3
    OFFSET_Z = 0
    SHADOW_MODE = Overhead Shadow
    FOOTPRINT -> CoordinateExtractor_3
    <REJECTED> -> SurfaceFootprintReplacer_3__Rejected_
SurfaceFootprintReplacer_3__Rejected_: Inspector
CoordinateExtractor_3
    LIST_NAME = _indices
    MODE = All Coordinates
    -> AttributeCreator_3
AttributeCreator_3
    ATTR_TABLE:
      SET_TO _x_end_wall
      SET_TO _y_end_wall
      SET_TO _x_start_wall
      SET_TO _y_start_wall
      SET_TO _y_min
      SET_TO _y_max
    -> PythonCaller_max_x
Note: Tried to add both max and min x in the / same caller but it gave overflow error
PythonCaller_max_x
    NEW_ATTRIBUTES = _x_end_wall
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outMax = {} # key = uuid, value = max coordinate
          outMin = {} # key = uuid, value = min coordinate
          for wall in lines:

              i = 0 # Index
              tmx = -99999999 # Temporary max x coordinate
              #tminx = float('inf') # Temporary min x coordinate
              tuuid = wall.getAttribute('_uuid') # Current UUID
              while True:
                  tx = wall.getAttribute('_indices{%d}.x' % i) # Current x coordinate
                  if tx == None:
                      break
                  if tx > tmx:
                      tmx = tx
                  #elif tx < tminx:
                      #tminx = tx
                  i += 1

              outMax[tuuid] = int(round(tmx))
              #outMin[tuuid] = round(tminx)
          return outMax #, outMin

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              # Tried with both max and min but got error (overflow in setAttribute)
              #maxX, minX = lineEndsFinder(self.featureList) # Returns dict with key:uuid; value:maxX
              maxX = lineEndsFinder(self.featureList) # Returns dict with key:uuid; value:maxX
              for f in self.featureList:
                  fuuid = f.getAttribute('_uuid') # uuid to use as key in the maxX dictionary
                  f.setAttribute("_x_end_wall", maxX[fuuid])
                  #f.setAttribute("_x_start_wall", minX[fuuid])
                  self.pyoutput(f)
    -> PythonCaller_min_x
PythonCaller_min_x
    NEW_ATTRIBUTES = _x_start_wall
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outMin = {} # key = uuid, value = min coordinate
          for wall in lines:

              i = 0 # Index
              tminx = float('inf') # Temporary min x coordinate
              tuuid = wall.getAttribute('_uuid') # Current UUID
              while True:
                  tx = wall.getAttribute('_indices{%d}.x' % i) # Current x coordinate
                  if tx == None:
                      break
                  if tx < tminx:
                      tminx = tx
                  i += 1

              outMin[tuuid] = int(round(tminx))
          return outMin

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              minX = lineEndsFinder(self.featureList) # Returns dict with key:uuid; value:maxX
              for f in self.featureList:
                  fuuid = f.getAttribute('_uuid') # uuid to use as key in the maxX dictionary
                  f.setAttribute("_x_start_wall", minX[fuuid])
                  self.pyoutput(f)
    -> PythonCaller_max_y
PythonCaller_max_y
    NEW_ATTRIBUTES = _y_max
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outMax = {} # key = uuid, value = min coordinate
          for wall in lines:

              i = 0 # Index
              tmy = -9999 # Temporary min x coordinate
              tuuid = wall.getAttribute('_uuid') # Current UUID
              while True:
                  ty = wall.getAttribute('_indices{%d}.y' % i) # Current x coordinate
                  if ty == None:
                      break
                  if ty > tmy:
                      tmy = ty
                  i += 1

              outMax[tuuid] = int(round(tmy))
          return outMax

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              maxY = lineEndsFinder(self.featureList) # Returns dict with key:uuid; value:maxX
              for f in self.featureList:
                  fuuid = f.getAttribute('_uuid') # uuid to use as key in the maxX dictionary
                  f.setAttribute("_y_max", maxY[fuuid])
                  self.pyoutput(f)
    -> PythonCaller_min_y
PythonCaller_min_y
    NEW_ATTRIBUTES = _y_min
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outMin = {} # key = uuid, value = min coordinate
          for wall in lines:

              i = 0 # Index
              tminy = float('inf') # Temporary min x coordinate
              tuuid = wall.getAttribute('_uuid') # Current UUID
              while True:
                  ty = wall.getAttribute('_indices{%d}.y' % i) # Current x coordinate
                  if ty == None:
                      break
                  if ty < tminy:
                      tminy = ty
                  i += 1

              outMin[tuuid] = int(round(tminy))
          return outMin

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              minY = lineEndsFinder(self.featureList) # Returns dict with key:uuid; value:maxX
              for f in self.featureList:
                  fuuid = f.getAttribute('_uuid') # uuid to use as key in the maxX dictionary
                  f.setAttribute("_y_min", minY[fuuid])
                  self.pyoutput(f)
    -> PythonCaller_start_end_y
PythonCaller_start_end_y
    NEW_ATTRIBUTES = _y_start_wall _y_end_wall
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outY = {} # key = uuid, value = min coordinate
          for wall in lines:

              tuuid = wall.getAttribute('_uuid') # Current UUID
              startX = wall.getAttribute('_x_start_wall')
              endX = wall.getAttribute('_x_end_wall')
              minY = wall.getAttribute('_y_min')
              maxY = wall.getAttribute('_y_max')

              if startX == endX:
                  startY = minY
                  endY = maxY
              elif minY == maxY:
                  startY = minY
                  endY = maxY
              else:
                  i = 0 # Index of coordinate
                  while True:
                      tx = wall.getAttribute('_indices{%d}.x' % i) # Current x coordinate
                      ty = wall.getAttribute('_indices{%d}.y' % i) # Current y coordinate
                      if tx == None:
                          break
                      else:
                          # This cannot be done where the attributes are read since the last will be a None object
                          tx = int(round(tx))
                          ty = int(round(ty))
                      if tx == startX:
                          if ty == minY:
                              startY = minY
                              endY = maxY
                          elif ty == maxY:
                              startY = maxY
                              endY = minY
                      i += 1

              outY[tuuid] = (startY, endY)
              starY = None
              endY = None

          return outY

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              startEndY = lineEndsFinder(self.featureList) # Returns dict with key:uuid; value:maxX
              for f in self.featureList:
                  fuuid = f.getAttribute('_uuid') # uuid to use as key in the maxX dictionary
                  f.setAttribute("_y_start_wall", startEndY[fuuid][0])
                  f.setAttribute("_y_end_wall", startEndY[fuuid][1])
                  self.pyoutput(f)
    -> AttributeRemover
AttributeRemover
    REMOVE_ATTRS = _y_max,_y_min
    -> CoordinateExtractor_End_Wall_Output (output)
CoordinateExtractor_End_Wall_Output (output)
CoordinateCounter
    CNT_ATTR = _coordcount_wall
    -> CoordinateExtractor_Start_Wall
CoordinateExtractor_Start_Wall
    IND = 0
    X_ATTR = _x_start_wall
    Y_ATTR = _y_start_wall
    MODE = Specify Coordinate
    Z_ATTR = _z_start_wall
    -> CoordinateExtractor_End_Wall
CoordinateExtractor_End_Wall
    IND = @Value(_coordcount_wall)-1
    X_ATTR = _x_end_wall
    Y_ATTR = _y_end_wall
    MODE = Specify Coordinate
    Z_ATTR = _z_end_wall

Bookmark: Walls -> 2D and finding start and end coordinates
Note: Need IFMELine geometry later and for that the SurfaceFootPrintReplacer is better BUT some walls becomes polygons instead of lines. How to handle? / Coordinates extracted to be able to handle line directions later.

FME custom transformer SurfaceNormalCalculator
This custom transformer calculates the coefficients of unit normal vector for each introduced polygon (attributes "normalX", "normalY", "normalZ"). The angle (attribute Slope) to the vertical is also derived from the direction of the surface normal vector. Values of 0 indicate perpendicular, 90 horizontal polygons. Furthermore, the 2D area is output in the attribute "signedArea2D" per polygon. Depending on the sign, a statement can be made about the orientation of the polygon. Negative values indicate polygons clockwise, positive counter-clockwise direction-oriented.
In order to obtain meaningful results, it is important to ensure that only planar polygons are initiated. All non-area features are routed unchanged through the rejected port.

INPUT (input)
    -> GeometryFilter
Note: use only closed polygons
GeometryFilter
    BREAK_AGG = No
    POINT -> Invalid (output)
    LINE -> Invalid (output)
    ARC -> Invalid (output)
    AREA -> CoordinateCounter
    ELLIPSE -> Invalid (output)
    TEXT -> Invalid (output)
    RASTER -> Invalid (output)
    SURFACE -> Invalid (output)
    SOLID -> Invalid (output)
    COLLECTION -> Invalid (output)
    NULL -> Invalid (output)
CoordinateCounter
    CNT_ATTR = _coordcount
    -> PythonCaller
PythonCaller
    NEW_ATTRIBUTES = normalX normalY normalZ Slope signedArea2D
    PYTHONSYMBOL = calcNormal
    PYTHONSOURCE:
      import math
      import fmeobjects
      # Template Function interface:
      def calcNormal(feature):

          counter0 = 0
          coordCount = feature.numVertices() - 1

          normalX = 0
          normalY = 0
          normalZ = 0
          areaTri = 0
          area = 0
          angle = 0

          # loop through the coordinates and calculate surface normal of the triangle formed by the
          # the point, its predecessor and its successor.
          while counter0 < coordCount:

              # get test coordinate and the ones before and after
              before = (counter0 + (coordCount - 1)) % coordCount
              after = (counter0 + (coordCount + 1)) % coordCount
              coords0 = feature.getCoordinate(before)
              coords1 = feature.getCoordinate(counter0)
              coords2 = feature.getCoordinate(after)

              # calculate normal
              x1 = coords0[0]
              x2 = coords1[0]
              x3 = coords2[0]

              y1 = coords0[1]
              y2 = coords1[1]
              y3 = coords2[1]

              z1 = coords0[2]
              z2 = coords1[2]
              z3 = coords2[2]

              normalX = normalX + ((y2-y1) * (z3-z1) - (y3-y1) * (z2-z1))
              normalY = normalY + ((z2-z1) * (x3-x1) - (z3-z1) * (x2-x1))
              normalZ = normalZ + ((x2-x1) * (y3-y1) - (x3-x1) * (y2-y1))

              counter0 = counter0 + 1

              # polygon area (Gauss area formula)
              areaTri = ((y2+y3)*(x2-x3))/2
              area = area + areaTri


          # normalize vector
          length = math.sqrt(normalX**2 + normalY**2 + normalZ**2)

          if length <> 0:
              normalX = normalX / length
              normalY = normalY / length
              normalZ = normalZ / length
          else:
              normalX = 0
              normalY = 0
              normalZ = 0

          # angle
          if normalZ <>0:
              angle = math.fabs(math.atan(math.sqrt(normalX**2+normalY**2)/normalZ)*(180/3.14))
          else:
              angle = 90


          # write normal to feature
          feature.setAttribute('normalX',normalX)
          feature.setAttribute('normalY',normalY)
          feature.setAttribute('normalZ',normalZ)
          feature.setAttribute('signedArea2D',area)
          feature.setAttribute('Slope',angle)
    -> AttributeRemover_3
AttributeRemover_3
    REMOVE_ATTRS = _coordcount
    -> Ok (output)
Ok (output)
Invalid (output)

FME custom transformer SlopeCalculator
This transformer calculates the slope of input polygons and surfaces.
It works by extracting the bounds of an input feature and comparing its maximum and minimum Z values. 
- If the difference is 0, then the surface is deemed flat with zero slope.
- If the difference is not zero, then the input feature is triangulated, and the slope of each of its triangles is calculated. The slope is presented as the average of the slopes of its triangles.
Input Ports 
    Input 
Input features must have geometry of type polygon or surface.
    Output Ports 
    Output 
Features are output with a new attribute with the slope of source data. 
_slope: Contains the value of slope in degrees.
    <Rejected> 
Features will be passed through this port if they are not of type polygon (area, ellipse) or surface. The attribute fme_rejection_code will be added to each feature with value INVALID_GEOMETRY_TYPE.
    Parameters 
This transformer has no parameters.
    Usage Notes
For best results, make sure that input surfaces are planar.

Input (input)
    -> GeometryFilter
Counter
    START = 0
    SCOPE = Local
    CNT_ATTR = SC_count
    DOMAIN = SC_count
    -> BoundsExtractor_2
Note: Extract face bounds
BoundsExtractor_2
    XMIN = _xmin
    YMAX = _ymax
    ZMIN = _zmin
    YMIN = _ymin
    XMAX = _xmax
    ZMAX = _zmax
    -> Tester_2
Note: Determine if surface is flat or sloped
Tester_2
    TEST_MODE = Automatic
    TEST_CLAUSE = TEST @Value(_zmin) = @Value(_zmax)
    BOOL_OP = OR
    PASSED -> AttributeCreator_4
    FAILED -> Triangulator
    FAILED -> FeatureMerger [REQUESTOR]
Note: Flat surfaces simply get 0 for slope
AttributeCreator_4
    ATTR_TABLE = SET_TO SLOPE = 0
    -> AttributeManager
Note: Add the calculated slope / to the original faces
FeatureMerger
    SUPPLIERS_FIRST = No
    IGNORE_NULLS = Yes
    JOIN_KEYS = @Value(SC_count) @Value(SC_count) AUTO
    ATTR_CONFLICT_RES = Use Requestor
    PROCESS_DUPS = No
    ATTR_ACCUM_MODE = Merge Supplier
    MERGE_TYPE = Attributes Only
    MERGED -> AttributeManager
Note: Clean up features
AttributeManager
    ATTR_TABLE:
      REMOVE SC_count
      REMOVE _xmax
      REMOVE _xmin
      REMOVE _ymax
      REMOVE _ymin
      REMOVE _zmax
      REMOVE _zmin
      RENAME_SET_VALUE SLOPE > _slope
    -> Output (output)
Output (output)
<Rejected> (output)

Bookmark: Validate geometry
GeometryFilter
    GEOM_PORT_NAMES = Area Ellipse Surface
    BREAK_AGG = No
    AREA -> Counter
    ELLIPSE -> Counter
    SURFACE -> Counter
    <UNFILTERED> -> AttributeCreator_5
AttributeCreator_5
    ATTR_TABLE = SET_TO fme_rejection_code = INVALID_GEOMETRY_TYPE
    -> <Rejected> (output)

Bookmark: Replace faces with triangles
Triangulator
    TRIANGLES -> Deaggregator_2
Deaggregator_2
    SPLIT_COMPOSITES = Yes
    GEOM_NAME_FIELD = _geometry_name
    PART_NUMBER_FIELD = _part_number
    LIST_ATTR_MODE_LOOKUP = LEAN
    MODE = Flatten One Level
    EXPLODE_INSTANCES = No
    DEAGGREGATED -> GeometryCoercer
GeometryCoercer
    KIND = fme_polygon
    CHECKZ = No
    COERCED -> CoordinateExtractor_2

Bookmark: Extract coordinates of the triangle vertices
CoordinateExtractor_2
    Z_DEFAULT = -9999
    IND = 0
    X_ATTR = _x0
    Y_ATTR = _y0
    MODE = Specify Coordinate
    Z_ATTR = _z0
    -> CoordinateExtractor_3
CoordinateExtractor_3
    Z_DEFAULT = -9999
    IND = 1
    X_ATTR = _x1
    Y_ATTR = _y1
    MODE = Specify Coordinate
    Z_ATTR = _z1
    -> CoordinateExtractor_4
CoordinateExtractor_4
    Z_DEFAULT = -9999
    IND = 2
    X_ATTR = _x2
    Y_ATTR = _y2
    MODE = Specify Coordinate
    Z_ATTR = _z2
    -> AttributeCreator

Bookmark: Calculate slopes
Note: Create two vectors that / connect the triangle's / vertices (from one vertex / to the other two)
AttributeCreator
    ATTR_TABLE:
      SET_TO _u1 = @Evaluate(@Value(_x0)-@Value(_x2))
      SET_TO _v1 = @Evaluate(@Value(_x1)-@Value(_x2))
      SET_TO _u2 = @Evaluate(@Value(_y0)-@Value(_y2))
      SET_TO _v2 = @Evaluate(@Value(_y1)-@Value(_y2))
      SET_TO _u3 = @Evaluate(@Value(_z0)-@Value(_z2))
      SET_TO _v3 = @Evaluate(@Value(_z1)-@Value(_z2))
    -> AttributeCreator_2
Note: Take a cross product of the / two vectors to find a vector / that is normal to the triangle
AttributeCreator_2
    ATTR_TABLE:
      SET_TO _nx = @Evaluate(@Value(_u2)*@Value(_v3)-@Value(_u3)*@Value(_v2))
      SET_TO _ny = @Evaluate(@Value(_u3)*@Value(_v1)-@Value(_u1)*@Value(_v3))
      SET_TO _nz = @Evaluate(@Value(_u1)*@Value(_v2)-@Value(_u2)*@Value(_v1))
    -> AttributeCreator_3
Note: Find the length of the normal's / projection on the x,y plane
AttributeCreator_3
    ATTR_TABLE = SET_TO _length = @Evaluate(@sqrt(@Value(_nx)*@Value(_nx)+@Value(_ny)*@Value(_ny)))
    -> AttributeCreator_6
Note: Find the triangle's slope: / - First find the absolute value / of its normal's slope. / - A plane's normal is perpendicular / to that plane, hence their slope / differs by 90 degrees (PI/2 radians)
AttributeCreator_6
    ATTR_TABLE = SET_TO _slope = @Evaluate(3.14159/2.0-@atan2(@abs(@Value(_nz)),@abs(@Value(_length))))
    -> AttributeCreator_7
Note: Convert from / radians to degrees
AttributeCreator_7
    ATTR_TABLE = SET_TO SLOPE = @Evaluate(@Value(_slope)*180.0/3.14159)
    -> StatisticsCalculator
Note: Find the average
StatisticsCalculator
    STATS_ATTRS = SLOPE
    MEAN_ATTR = SLOPE
    PREPEND_ATTR_NAME_CHOICE = For multiple results only
    GROUP_BY = SC_count
    COMPUTE_HISTOGRAM = NO
    SUMMARY -> FeatureMerger [SUPPLIER]

FME custom transformer mainWallFinder

Parameters:
- WALLHEIGHTNEW = @Value(wallHeightNEW)   # wallHeightNEW
- WALLHEIGHTOLD = @Value(wallHeightOLD)   # wallHeightOLD
- WALLORDERID = @Value(wallOrderID)   # wallOrderID

Note: Wall surfaces from the building
inputWalls (input)
    -> Aggregator_2
    -> SurfaceNormalCalculator
    -> inputWalls_-__NeighborFinder_CANDIDATE
inputWalls_-__NeighborFinder_CANDIDATE: Junction
    -> NeighborFinder [CANDIDATE]
    -> FeatureMerger [SUPPLIER]
PythonCaller_mainWallFinder
    NEW_ATTRIBUTES = closeNode
    PYTHONSYMBOL = FeatureProcessor
    PYTHONSOURCE:
      import fme
      import fmeobjects
      import math


      # Template Class Interface:
      # When using this class, make sure its name is set as the value of
      # the 'Class or Function to Process Features' transformer parameter
      class FeatureProcessor(object):
          def __init__(self):
              self.lineDict = {} # For nodes (intersection points)
              self.centrePoint = None

          def input(self,feature): # This function is called every time a feature is added
              if feature.getAttribute('buildingCentre'):
                  f = feature.getGeometry()
                  self.centrePoint = f.getXYZ()
              elif feature.getAttribute('wallOrderID')  >=0 :
                  if feature.getAttribute('wallOrderID') in self.lineDict.keys():
                      self.lineDict[feature.getAttribute('wallOrderID')].append(feature)
                  else:
                      self.lineDict[feature.getAttribute('wallOrderID')] = [feature]


          def close(self):
              # To find line segments starting at the building's walls
              closeLine = [] # Saving all line segment touchg walls. Not really needed
              mainWall = (999999, -1) # Saving closest wall only
              for key in self.lineDict:
                  tempMin = 999999
                  featureList = self.lineDict[key]
                  for lineSeg in featureList:
                      geo = lineSeg.getGeometry()
                      pointList = geo.getPoints()
                      for p in pointList:
                          tempXYZ = p.getXYZ()
                          tempDist = math.sqrt((self.centrePoint[0]-tempXYZ[0])**2 + (self.centrePoint[1]-tempXYZ[1])**2)
                          if tempDist < tempMin:
                              tempMin = tempDist
                              tempFea = lineSeg
                              tempLen = lineSeg.getAttribute('_length')

                  if tempLen < mainWall[0]:
                      mainWall = (tempLen, lineSeg.getAttribute('wallOrderID'), tempFea)
                      mainWallKey = key # To acces the shorest intersection line later

                  closeLine.append((tempFea,tempLen))

                  print closeLine
                  print mainWall
              mainWallFeature = mainWall[2]
              newFeature = fmeobjects.FMEFeature()
              newFeature.setGeometry(mainWallFeature.getGeometry())
              newFeature.setAttribute('closeNode', True)
              self.pyoutput(newFeature)
    -> NeighborFinder [BASE]
NeighborFinder
    INSERT_VERTEX = No
    MEASURES_FROM_CANDIDATE = Yes
    CANDIDATES_FIRST = No
    ATTR_ACCUM_MODE = Only Use Candidate
    TREAT_POLYGON_AS = Lines
    MEASURE_TYPE = Continuous
    MODE = Bases and Candidates
    K = 1
    MATCHED -> FeatureMerger [REQUESTOR]
FeatureMerger
    SUPPLIERS_FIRST = No
    IGNORE_NULLS = No
    JOIN_KEYS = @Value(wallOrderID) @Value(wallOrderID) AUTO
    ATTR_CONFLICT_RES = Use Requestor
    PROCESS_DUPS = No
    ATTR_ACCUM_MODE = Merge Supplier
    MERGE_TYPE = Attributes and Geometry
    REJECT_NULL_MISSING_KEYS = No
    MERGED -> mainWallFinder_Output (output)
mainWallFinder_Output (output)

Bookmark: Finding intersections points between roads and surface normals of the walls.
Note: The features to find the shortest distance from. / In this case roads and biking paths.
Intersector_Input (input)
    -> Intersector
Note: Saving normal from wall instead since there a / re problem with normals for donuts.
SurfaceNormalCalculator
    Ok -> CenterPointReplacer_walls
CenterPointReplacer_walls
    MODE = Center Point
    POINT -> Extruder_2
Note: Extruding from centre point in / surface normal direction.
Extruder_2
    DISTANCE = 1000
    EXTRUSION_Y = @Value(normalY)
    EXTRUSION_Z = 0.0
    DIRECTION = Specified
    EXTRUSION_X = @Value(normalX)
    EXTRUDED -> Intersector
Intersector
    SEPARATE_COLLINEAR_SEGMENTS = No
    DEAGGREGATE_INPUT = Yes
    ATTRS_ACCUM_MODE = Use Attributes From One Feature
    PERFORM_SELF_INTERSECTION = No
    OV_ATTR = _overlaps
    DUPLICATE_Z_NODES = No
    MEASURE_TYPE = Continuous
    GENERATE_LIST_DROP = NO
    SEG_ATTR = _segments
    INTERSECTED -> LengthCalculator

Bookmark: To get centre of building
Aggregator_2
    ATTR_TO_TRAIT = Yes
    ACCUM_ATTRS_NAME = Use Attributes From One Feature
    SEP = ,
    AGGREGATE_TYPE = Homogeneous Collection (If Possible)
    ID_SELECTION = ID and Parent ID
    ORDERED = No
    PRESERVE_ID = No
    MODE = Geometry - Assemble One Level
    AGGREGATE -> CenterPointReplacer_building
CenterPointReplacer_building
    MODE = Center Point
    POINT -> AttributeCreator_3
AttributeCreator_3
    ATTR_TABLE = SET_TO buildingCentre = 1
    -> PythonCaller_mainWallFinder

Bookmark: Getting length of intersection lines
LengthCalculator
    DIM = 2
    LEN_ATTR = _length
    MULT = 1
    -> Sorter_2
Sorter_2
    SORT_PARM = _length NUMERIC ASCENDING
    SORTED -> Counter_IntersectionLines
Counter_IntersectionLines
    START = 0
    SCOPE = Local
    CNT_ATTR = _countIntersectionLines
    DOMAIN = counter
    -> AttributeKeeper_3
AttributeKeeper_3
    KEEP_ATTRS = _countIntersectionLines,wallOrderID,_length
    -> PythonCaller_mainWallFinder

FME custom transformer BuildingHeightCheckerCurrent

mainWallFinder_2 (input)
    -> 2DForcer_3
mainWallFinder (input)
    -> HullAccumulator
DevelopmentPlan_Input (input)
    -> Junction_6
Note: Only to visualilse the 16 / elevation points.
FeatureColorSetter [off]
    FILL_COLOR = 0.666667,0,0
    MODE = Fixed
    COLOR = 0.666667,0,0
    COLORED -> FeatureColorSetter_Colored
FeatureColorSetter_Colored: Inspector [off]

Bookmark: Creating the horisontal plane representing mean ground elevation.
2DForcer_3
    2D -> BoundsExtractor
    2D -> HullAccumulator_2
AttributeKeeper_4
    KEEP_ATTRS = _angle,pointElevation,wallHeightOLD,_closest_candidate_x,_candidate_angle,_distance,_closest_base_x,wallHeightNEW,_closest_candidate_y,_closest_base_y,wallOrderID,zOffset
    -> Aggregator_2
    -> PythonCaller_GroundPointLifter
Note: Calculates mean ground elevation
PythonCaller_GroundPointLifter
    NEW_ATTRIBUTES = meanElevation
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.pointList = []
              self.totElevation = 0
              self.elevOK = None

          def input(self,feature): # This function is called every time a feature is added
              if not feature.hasGeometry():
                  self.elevOK = feature.getAttribute('elevOK')
              else:
                  self.pointList.append(feature)
                  self.totElevation += feature.getAttribute('pointElevation')

          def close(self):
              if not self.elevOK:
                  print 'Elevation points are not including the highest and lowest points'
              else:
                  # Mean elevation of the ground around the building
                  meanElevation = self.totElevation*1.0/len(self.pointList)
                  # Iterating over all points and assigning z-value
                  for tempPoint in self.pointList:
                      tp = tempPoint.getGeometry()
                      tp.setZ(tempPoint.getAttribute('pointElevation'))
                      tempPoint.setGeometry(tp)
                      tempPoint.setAttribute('meanElevation', meanElevation)

                      self.pyoutput(tempPoint)
    -> PointOnAreaOverlayer_2 [POINT]
    -> FeatureColorSetter
PointOnAreaOverlayer_2
    POLYS_FIRST = No
    DEAGGREGATE_INPUT = Yes
    ATTR_CONFLICT_RES = Use Original
    OV_ATTR = _overlaps
    ATTR_ACCUM_MODE = Merge Incoming
    CANDIDATE_LIST_ATTRS_TO_INCLUDE_MODE = Selected Attributes
    AREA -> Offsetter_3
Note: Lifting the plane to the mean ground level.
Offsetter_3
    YOFF = 0
    XOFF = 0
    ZOFF = @Value(meanElevation)
    MODE = Cartesian Coordinate
    OFFSET -> FeatureColorSetter_2
    <REJECTED> -> Offsetter_3__Rejected_
FeatureColorSetter_2
    FILL_COLOR = 0.666667,0,0
    MODE = Fixed
    COLOR = 0.666667,0,0
    COLORED -> PythonCaller_heightChecker
Offsetter_3__Rejected_: Inspector

Bookmark: Finding wall lenghts
  Calculates lenght of each side of the buidling
BoundsExtractor
    XMIN = _xmin
    YMAX = _ymax
    ZMIN = _zmin
    YMIN = _ymin
    XMAX = _xmax
    ZMAX = _zmax
    -> PythonCaller_EndPointFinder
PythonCaller_EndPointFinder
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.lineList = []

          def input(self,feature): # This function is called every time a feature is added
              self.lineList.append(feature)

          def close(self):

              # Iterating over all walls to keep endpoints only
              for wallLine in self.lineList:

                  xMax = wallLine.getAttribute('_xmax')
                  xMin = wallLine.getAttribute('_xmin')
                  yMax = wallLine.getAttribute('_ymax')
                  yMin = wallLine.getAttribute('_ymin')
                  inLine = wallLine.getGeometry() # We get the geometry as a face

                  # Have not found a way of checking what geometry type the area is
                  # so using try to see if it is donut och polygon
                  try:
                      # Only outer boundary is interesting (i.e. openings not relevant)
                      pl = inLine.getOuterBoundaryAsCurve()
                  except:
                      pl = inLine.getBoundaryAsCurve()

                  pointList = pl.getPoints()

                  candidatePoints = []

                  # Looping over all points in the list keeping only those that include one
                  # boundary coordinate as candidates. Other points cannot be endpoints.
                  for tempPoint in pointList:
                      tempXYZ = tempPoint.getXYZ()
                      if xMax == tempXYZ[0] or xMin == tempXYZ[0] or yMax == tempXYZ[1] or yMin == tempXYZ[1]: # No need to check ground level points

                          candidatePoints.append(tempPoint)


                  currentLen = 0

                  for startIndex in xrange(len(candidatePoints)):
                      tempStart = candidatePoints[startIndex]
                      for endIndex in xrange(len(candidatePoints)):
                          if not startIndex == endIndex:
                              tempend = candidatePoints[1]
                              tempLen = sqrt((tempStart.getXYZ()[0]-tempend.getXYZ()[0])**2 + (tempStart.getXYZ()[1]-tempend.getXYZ()[1])**2)
                              if tempLen > currentLen:
                                  currentLen = tempLen
                                  currentStartIndex = startIndex
                                  currentEndIndex = endIndex

                  newLine = fmeobjects.FMELine([candidatePoints[currentStartIndex].getXYZ(), candidatePoints[currentEndIndex].getXYZ()])

                  wallLine.setGeometry(newLine)

                  self.pyoutput(wallLine)
    -> LengthCalculator
LengthCalculator
    DIM = 2
    LEN_ATTR = _length
    MULT = 1
    -> PythonCaller_NumberOfLineSplits

Bookmark: Creating 16 points along the building walls used to derive mean ground elevation
Note: Calculates how many points to include for / each side of the building.
PythonCaller_NumberOfLineSplits
    NEW_ATTRIBUTES = nbrLines nbrLinesDense
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.lineList = []
              self.totLen = 0
              self.nbrPoints = 16.0 # Number of points to calculate mean ground elevation

          def input(self,feature): # This function is called every time a feature is added
              self.lineList.append(feature)
              self.totLen += feature.getAttribute('_length')

          def close(self):

              lineFractions = []
              nbrPoints = []

              for wallLine in self.lineList:
                  lineFractions.append(wallLine.getAttribute('_length')/self.totLen)
                  # Number of line segments to split into
                  np = round(wallLine.getAttribute('_length')/self.totLen*self.nbrPoints)
                  nbrPoints.append(np)

                  # Creates points with a distance of half the DEM resolution to chekc that the highest and lowest
                  # elevation point is included among the points used to derived mean ground elevation.
                  npDense = round(wallLine.getAttribute('_length')/float(FME_MacroValues['DEM_resolution'])*2.0)

                  wallLine.setAttribute('nbrLines', np)
                  wallLine.setAttribute('nbrLinesDense', npDense)

                  self.pyoutput(wallLine)

              if sum(nbrPoints) != self.nbrPoints:
                  print 'WARNING!!!, number of line segments is not {}'.formatt(self.nbrPoints)
    -> IterativeSnipper
    -> IterativeSnipper_2

Bookmark: Walls -> points
  Splits the walls of the building into lines (16 to calculate mean ground elevation) and replaces the lines with a point at the startpoint of the line. Start is used to get points at the corners of the buidling.
IterativeSnipper
    SnipLength = @Value(nbrLines)
    SNIPMODE = ToNumber
    -> LengthCalculator_2
LengthCalculator_2
    DIM = 2
    LEN_ATTR = _length
    MULT = 1
    -> Tester_2
Tester_2
    TEST_MODE = Automatic
    TEST_DESCRIPTION = ""
    TEST_CLAUSE = TEST @Value(_length) > 0.1
    BOOL_OP = OR
    PASSED -> CoordinateExtractor_3
CoordinateExtractor_3
    IND = 0
    X_ATTR = _xPoint
    Y_ATTR = _yPoint
    MODE = Specify Coordinate
    Z_ATTR = _zPoint
    -> PythonCaller_PointCreator
Note: Replaces the line geometries with / a point at the start point of the line.
PythonCaller_PointCreator
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.lineList = []

          def input(self,feature):
              self.lineList.append(feature)

          def close(self):
              for l in self.lineList:
                  # Reading coords of first point of the line
                  x = l.getAttribute('_xPoint')
                  y = l.getAttribute('_yPoint')
                  z = l.getAttribute('_zPoint')

                  newPoint = fmeobjects.FMEPoint(x, y, z)
                  l.setGeometry(newPoint)
                  self.pyoutput(l)
    -> NeighborFinder [BASE]

Bookmark: Finding max and min elevation for the dense points.
  Finding max and min elevation for the dense points (distance = halv DEM resolution) to confirm that the highest and lowest points in teh DEM around the buidling are included among the 16 points used to derive mean ground elevation.
IterativeSnipper_2
    SnipLength = @Value(nbrLinesDense)
    SNIPMODE = ToNumber
    -> LengthCalculator_3
LengthCalculator_3
    DIM = 2
    LEN_ATTR = _length
    MULT = 1
    -> Tester_3
Tester_3
    TEST_MODE = Automatic
    TEST_DESCRIPTION = ""
    TEST_CLAUSE = TEST @Value(_length) > 0.1
    BOOL_OP = OR
    PASSED -> CenterPointReplacer_3
CenterPointReplacer_3
    MODE = Center Point
    POINT -> NeighborFinder_2 [BASE]
from_DEM (input)
    -> CoordinateExtractor_2
CoordinateExtractor_2
    IND = 0
    X_ATTR = _x
    Y_ATTR = _y
    MODE = Specify Coordinate
    Z_ATTR = _z
    -> AttributeCreator_4
AttributeCreator_4
    ATTR_TABLE = SET_TO pointElevation = @Value(_z)
    -> AttributeKeeper_5
AttributeKeeper_5
    KEEP_ATTRS = pointElevation
    -> NeighborFinder_2 [CANDIDATE]
NeighborFinder_2
    INSERT_VERTEX = No
    MEASURES_FROM_CANDIDATE = Yes
    ATTR_CONFLICT_RES = Use Base
    CANDIDATES_FIRST = No
    ATTR_ACCUM_MODE = Merge Candidate
    TREAT_POLYGON_AS = Lines
    MEASURE_TYPE = Continuous
    MODE = Bases and Candidates
    K = 1
    MATCHED -> AttributeKeeper_6
    <REJECTED> -> NeighborFinder__Rejected__2
AttributeKeeper_6
    KEEP_ATTRS = _angle,pointElevation,wallHeightOLD,_closest_candidate_x,_candidate_angle,_distance,_closest_base_x,wallHeightNEW,_closest_candidate_y,_closest_base_y,wallOrderID,zOffset
    -> Aggregator_3
NeighborFinder__Rejected__2: Inspector

Bookmark: Plane for height visualisation
  Creating a plane extending with the buffer amount outside teh building. Used for visualisation of mean ground surface later.
HullAccumulator_2
    HULLTYPE_PARAM = Convex ()
    3DMODE_PARAM = 2D
    HULL -> Generalizer
Generalizer
    ALG_TEXT = Douglas (Generalize)
    TOLERANCE = 1
    PRESERVE = No
    -> Bufferer
Bufferer
    CORNER_STYLE = Miter
    MITER_LIMIT = 3
    OFFSET = 3
    ANGLE = 22.5
    CAP_STYLE = None
    BUFFERED -> PointOnAreaOverlayer_2 [AREA]

Bookmark: To find in which area the building is located
HullAccumulator
    HULLTYPE_PARAM = Convex ()
    3DMODE_PARAM = 2D
    HULL -> Clipper_3 [CLIPPER]
Note: Detailed plan areas
Junction_6
    -> Clipper_3 [CLIPPEE]
Clipper_3
    MISSING_VAL_MODE = Compute
    DEFAULT_VAL = 0
    ATTR_CONFLICT_RES = Use Clippee
    ATTR_ACCUM_MODE = Merge Clipper
    CLIP_TYPE = Multiple Clippers
    CONNECT_Z_MODE = First Wins
    VAL_SOURCE = Clippee Only
    CREATE_AGGREGATES = Yes
    CLIPPED_ATTR = _clipped
    BOUNDARY_CASES = Treat as Inside
    MEASURE_TYPE = Continuous
    LINES_AS_SEGMENTS = No
    PRESERVE_CLIPPEE_EXTENTS = No
    INSIDE -> PythonCaller_heightChecker

Bookmark: Checking min and max elevation
  Checking that the highest and lowest points are included with the 16 points used to find mean ground elevation.
Aggregator_3
    ACCUM_ATTRS_NAME = Merge Incoming Attributes
    SEP = ,
    AGGREGATE_TYPE = Homogeneous Collection (If Possible)
    ORDERED = No
    LIST_ATTRS_TO_INCLUDE = pointElevation
    MODE = Geometry - Assemble One Level
    LIST_NAME = pointElevationList
    AGGREGATE -> ListRangeExtractor_2
ListRangeExtractor_2
    SRC_LIST = pointElevationList{}.pointElevation
    MIN = _minElevDense
    MAX = _maxElevDense
    -> PythonCaller_GroundPointLifter_2
Aggregator_2
    ACCUM_ATTRS_NAME = Merge Incoming Attributes
    SEP = ,
    AGGREGATE_TYPE = Homogeneous Collection (If Possible)
    ORDERED = No
    LIST_ATTRS_TO_INCLUDE = pointElevation
    MODE = Geometry - Assemble One Level
    LIST_NAME = pointElevationList
    AGGREGATE -> ListRangeExtractor
ListRangeExtractor
    SRC_LIST = pointElevationList{}.pointElevation
    MIN = _minElev
    MAX = _maxElev
    -> PythonCaller_GroundPointLifter_2
Note: Checks that the min and max / elevations are included with / the 16 points.
PythonCaller_GroundPointLifter_2
    NEW_ATTRIBUTES = elevOK
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.pointList = []
              self.pointListDense = []


          def input(self,feature): # This function is called every time a feature is added
              if feature.getAttribute('_minElevDense'):
                  self.pointListDense.append(feature)
              elif feature.getAttribute('_minElev'):
                  self.pointList.append(feature)

          def close(self):
              # Checking that min and max elevations are included in the 16 points
              minElevDiff = float(self.pointList[0].getAttribute('_minElev')) - float(self.pointListDense[0].getAttribute('_minElevDense'))
              maxElevDiff = float(self.pointList[0].getAttribute('_maxElev')) - float(self.pointListDense[0].getAttribute('_maxElevDense'))

              # Creating a new feature with the attribute elevOK with the value True if highest
              # and lowest points of teh building are included in the 16 points.
              nf = fmeobjects.FMEFeature()
              if abs(minElevDiff) < 0.01 and abs(maxElevDiff) < 0.01:
                  nf.setAttribute('elevOK', True)
              else:
                  nf.setAttribute('elevOK', False)

              self.pyoutput(nf)
    -> PythonCaller_GroundPointLifter

Bookmark: Getting elevation for the 16 points along the buildiing walls.
from_DEM_2 (input)
    -> CoordinateExtractor
CoordinateExtractor
    IND = 0
    X_ATTR = _x
    Y_ATTR = _y
    MODE = Specify Coordinate
    Z_ATTR = _z
    -> AttributeCreator_3
AttributeCreator_3
    ATTR_TABLE = SET_TO pointElevation = @Value(_z)
    -> AttributeKeeper_3
AttributeKeeper_3
    KEEP_ATTRS = pointElevation
    -> NeighborFinder [CANDIDATE]
NeighborFinder
    INSERT_VERTEX = No
    MEASURES_FROM_CANDIDATE = Yes
    ATTR_CONFLICT_RES = Use Base
    CANDIDATES_FIRST = No
    ATTR_ACCUM_MODE = Merge Candidate
    TREAT_POLYGON_AS = Lines
    MEASURE_TYPE = Continuous
    MODE = Bases and Candidates
    K = 1
    MATCHED -> AttributeKeeper_4
    <REJECTED> -> NeighborFinder__Rejected_
NeighborFinder__Rejected_: Inspector

Bookmark: Checking if the building heigth is allowed according to the development plan.
  Checks the building height against the development plan and displays the ground elevation plane. 
  If the building is too high, a horisontal plane representing max allowed building height is visualised.
Note: Checks if building height is allowed. / Adds the attribute heightOK with the / value True or False.
PythonCaller_heightChecker
    NEW_ATTRIBUTES = heightOK maxHeight
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.byggnadsHojd = None
              self.by = None
              self.maxByggnadsHojd = None

          def input(self,feature): # This function is called every time a feature is added
              if feature.getAttribute('gml_parent_property') == 'egenskapsbestammelse':
                  self.maxByggnadsHojd = float(feature.getAttribute('byggnadshojd'))
              elif feature.getAttribute('wallHeightOLD'):
                  self.byggnadsHojd = float(feature.getAttribute('wallHeightOLD'))
                  self.by = feature


          def close(self):

              # Checing if the building is lower than the allowed height with the
              # allowed toleracne of 10 cm.
              if self.byggnadsHojd - self.maxByggnadsHojd < 0.1:
                  self.by.setAttribute('heightOK', True)
              else:
                  self.by.setAttribute('heightOK', False)
                  nf = self.by.clone()
                  geo = nf.getGeometry()
                  nl = geo.getBoundaryAsCurve()
                  np = nl.getPoints()

                  # Horisontal surface so we can take z from any point
                  newZ = np[0].getXYZ()[2] + self.maxByggnadsHojd
                  # new pointlist with coordinates lifted to max building height
                  [p.setZ(newZ) for p in np]
                  liftedXYZ = [p.getXYZ() for p in np]
                  liftedLine = fmeobjects.FMELine(liftedXYZ)
                  liftedPoly = fmeobjects.FMEPolygon(liftedLine)
                  nf.setGeometry(liftedPoly)
                  nf.setAttribute('maxHeight', 'True')
                  self.pyoutput(nf)

              self.pyoutput(self.by)
    -> TestFilter_6
TestFilter_6
    DEFAULT_VALUE = <UNFILTERED>
    TEST_LIST = BOOL_OP,OR,COMPOSITE_TEST,<Unused>,TEST_CLAUSE,"TEST @Value(maxHeight) = True",maxHeight
    maxHeight -> maxHeight_if_too_high (output)
    <UNFILTERED> -> groundElevation (output)
maxHeight_if_too_high (output)
groundElevation (output)

FME custom transformer IFC2CityGML_GetGrandParentId

Parameters:
- ATTR_TO_ENCODE =   # " " Attribute to Encode
- DEST_ATTR = gml_parent_id   # TYPE:varchar(200) Destination Attribute

BinaryEncoder_Input (input)
    -> BinaryEncoder
BinaryEncoder
    DEST_ATTR = _parent_id
    ENCODING_TYPE = HEX
    ATTR_TO_ENCODE = $(ATTR_TO_ENCODE)
    -> VariableRetriever
VariableRetriever
    SCOPE = Global
    VARNAME = p@Value(_parent_id)
    VALUE_ATTR = _gparent_id
    -> BinaryDecoder
BinaryDecoder
    ATTR_ENCODING = utf-8
    DEST_ATTR = $(DEST_ATTR)
    ATTR_TO_DECODE = _gparent_id
    ENCODING_TYPE = HEX
    -> Output (output)
Output (output)

FME custom transformer detaljPlanReader

Parameters:
- XML_PARENT_CHILD_POS = @Value(xml_parent_child_pos)   # Xml Parent Child Pos
- DP_OMRADE.ID = @Value(DP_Omrade.id)   # Dp Omrade.id
- UUID = @Value(uuid)   # uuid
- GML_ID = @Value(gml_id)   # Gml Id
- XML_PARENT_ID = @Value(xml_parent_id)   # Xml Parent Id
- ANVANDNINGSSLAG = @Value(anvandningsslag)   # anvandningsslag
- PLUS.HREF = @Value(plus.href)   # plus.href
- MINUS.HREF = @Value(minus.href)   # minus.href
- OMRADE.XLINK_HREF = @Value(omrade.xlink_href)   # Omrade.xlink Href
- BETECKNING = @Value(beteckning)   # beteckning
- BESTAMMELSETYP = @Value(bestammelsetyp)   # bestammelsetyp
- XML_ID = @Value(xml_id)   # Xml Id
- URSPRUNGLIG = @Value(ursprunglig)   # ursprunglig

Aggregator_Input (input)
    -> Aggregator
Note: Create list with gränser per område
Aggregator
    ACCUM_ATTRS_NAME = Merge Incoming Attributes
    SEP = ,
    ORDERED = No
    LIST_ATTRS_TO_INCLUDE = minus.href plus.href xml_parent_child_pos
    GROUP_BY = xml_parent_id
    MODE = Attributes Only
    LIST_NAME = childList
    AGGREGATE -> PolygonCreator
AttributeCreator_2_Input (input)
    -> AttributeCreator_2
Note: Create ID for later join
AttributeCreator_2
    ATTR_TABLE = SET_TO ID_join = #@Value(gml_id)
    -> PolygonCreator
Note: Creates polygons over Områden.
PolygonCreator: PythonCaller
    PYTHONSYMBOL = FeatureProcessor
    PYTHONSOURCE:
      import fme
      import fmeobjects

      # Finds and returns the requested gräns
      def gransFinder(id,gransList):
          for grans in gransList:
              if grans.getAttribute('ID_join') == id:
                  return grans

      # Finds first line segment in a boundary, either outer or inner polygon
      def initialBoundaryLine(polygonBoundaryParts):
          geo = polygonBoundaryParts.getGeometry()

          nbrLines = geo.numParts()

          # Taking first part of the FMEPath
          polygonBoundary = geo.getPartAt(0)

          if type(polygonBoundary) == fmeobjects.FMEArc:
              polygonBoundary = polygonBoundary.getAsLine()

          # Iterating over the parts in the FMEPath object
          for tp in xrange(1,nbrLines):
              tpl = geo.getPartAt(tp) # Next part (at index tp)

              # Needs to be an FMELine
              if type(tpl) == fmeobjects.FMEArc:
                  tpl = tpl.getAsLine()

              polygonBoundary.appendLine(tpl)

          return polygonBoundary

      # #################################################################
      # FeatureProcessor
      # #################################################################
      class FeatureProcessor(object):
          def __init__(self):
              self.omrade = []
              self.grans = []

          # Saving in different lists depending on if the feature is a gräns or område
          def input(self,feature):
              if feature.hasGeometry():
                  self.grans.append(feature)
              else:
                  self.omrade.append(feature)

          def close(self):

              # Iterating over all Områden sent to the PythonCaller
              for omr in self.omrade:
                  boundaryList = []
                  tempGrans = True # Will stop the loop after last item is found (temp = None)
                  index = 0 # Index of "Gräns"
                  innerIndex = 0 # For keeping track of holes
                  firstLine = True # If first line segment of a gräns

                  #Looping over all "gränser" in current "Område"
                  while tempGrans != None:
                      tempGrans = omr.getAttribute('childList{%i}.xml_parent_child_pos' % (index))

                      # Already found last "gräns" of the "område"
                      if not tempGrans:
                          break
                      tempGrans = int(tempGrans)

                      if not tempGrans == index: # To break in case something is wrong wth indices
                          print 'Index not correct'
                          break

                      # Retreiving the next segment and finding direction.
                      minusTest = omr.getAttribute('childList{%i}.minus.href' % (index))
                      if minusTest != None:
                          minus = True
                          tempGransID = minusTest
                      else:
                          minus = False
                          tempGransID = omr.getAttribute('childList{%i}.plus.href' % (index))

                      # Building line
                      # This part is for the first "Gräns" either in the outer (index == 0) polygon or
                      # a hole (innerIndex >= 1)
                      if firstLine:
                          partOne = gransFinder(tempGransID, self.grans)
                          polygonBoundary = initialBoundaryLine(partOne)
                          firstLine = False
                          if minus:
                              polygonBoundary.reverse()


                      # From the second "gräns" in the list.
                      else:
                          polygonBoundaryParts = gransFinder(tempGransID, self.grans)

                          geo = polygonBoundaryParts.getGeometry()

                          nbrLines = geo.numParts()

                          tmpLine = geo.getPartAt(0)

                          if type(tmpLine) == fmeobjects.FMEArc:
                              tmpLine = tmpLine.getAsLine()

                          #Iterating over the of the parts in the FMEPath object
                          for tp in xrange(1,nbrLines):

                              tpl = geo.getPartAt(tp)

                              if type(tpl) == fmeobjects.FMEArc:
                                  tpl = tpl.getAsLine()

                              tmpLine.appendLine(tpl)

                          if minus:
                              tmpLine.reverse()

                          polygonBoundary.appendLine(tmpLine)

                      # True if a closed polygon is found.
                      if polygonBoundary.isClosed(False): # False => not considering 3D
                          firstLine = True # Next will be first line of an inner polygon (if existing)
                          innerIndex += 1 # Counting inner polygons
                          boundaryList.append(polygonBoundary) # Appending current polygon to list
                          polygonBoundary = None

                      index += 1

                  # Final part: Creating the polygons incl. holes if present
                  # Creating a polygon with the outer boundary by popping it from the list of ploygons
                  if boundaryList:
                      outerPoly = fmeobjects.FMEDonut(boundaryList.pop(0))
                      # Iterating over all inner polygons that were found (the ouoter is already removed above)
                      for omrPoly in boundaryList:
                          innerPoly = fmeobjects.FMEDonut(omrPoly)
                          outerPoly.addInnerBoundaryCurve(omrPoly)

                      omr.setGeometry(outerPoly)

                      self.pyoutput(omr)
    -> FeatureMerger_2 [REQUESTOR]
PythonCaller_Byggnadshojd_Input (input)
    -> PythonCaller_Byggnadshojd
Note: Finds byggnadshöjd / (Other heights not considered)
PythonCaller_Byggnadshojd
    NEW_ATTRIBUTES = byggnadshojd
    PYTHONSYMBOL = processFeature
    PYTHONSOURCE:
      import fme
      import fmeobjects

      # Template Function interface:
      # When using this function, make sure its name is set as the value of
      # the 'Class or Function to Process Features' transformer parameter
      def processFeature(feature):

          if feature.getAttribute('bestammelsetyp')  == 'DP_KM_Eg_Omfatt_Byggnadshojd':
              byHojd = feature.getAttribute('beteckning')
              byHojd = byHojd.replace(',', '.')
              byHojd = float(byHojd)
              feature.setAttribute('byggnadshojd', byHojd)
    -> FeatureMerger_Egenskap [SUPPLIER]
    -> GeometryFilter
GeometryFilter
    GEOM_PORT_NAMES = Point
    BREAK_AGG = No
    POINT -> PointOnAreaOverlayer [POINT]
    <UNFILTERED> -> GeometryFilter_2
Note: Unfiltered, regulations with link, no geometry.
GeometryFilter_2
    GEOM_PORT_NAMES = Line Arc Null
    BREAK_AGG = No
    NULL -> FeatureMerger_4 [SUPPLIER]
FeatureMerger_Anvandning_Supplier (input)
    -> FeatureMerger_Anvandning [SUPPLIER]
FeatureMerger_Requestor (input)
    -> FeatureMerger [REQUESTOR]
FeatureMerger_Supplier (input)
    -> FeatureMerger [SUPPLIER]
Note: Needs xml_id from the / XML-reader to join with lines.
FeatureMerger
    SUPPLIERS_FIRST = No
    IGNORE_NULLS = No
    JOIN_KEYS = @Value(gml_id) @Value(DP_Omrade.id) AUTO
    ATTR_CONFLICT_RES = Use Requestor
    PROCESS_DUPS = No
    ATTR_ACCUM_MODE = Merge Supplier
    MERGE_TYPE = Attributes Only
    REJECT_NULL_MISSING_KEYS = No
    MERGED -> AttributeKeeper
AttributeKeeper
    KEEP_ATTRS = xml_id,gml_id,xml_fragment,DP_Omrade.id,gml_parent_id
    -> AttributeCreator
AttributeCreator
    ATTR_TABLE = SET_TO ID_join = #@Value(DP_Omrade.id)
    -> FeatureMerger_Egenskap [REQUESTOR]
AttributeRemover
    REMOVE_ATTRS = minus,plus
    -> FeatureMerger_2 [SUPPLIER]
Note: Adding Geometries to bestämmelser
FeatureMerger_2
    SUPPLIERS_FIRST = No
    IGNORE_NULLS = No
    JOIN_KEYS = @Value(xml_parent_id) @Value(xml_id) AUTO
    ATTR_CONFLICT_RES = Use Requestor
    PROCESS_DUPS = No
    ATTR_ACCUM_MODE = Merge Supplier
    MERGE_TYPE = Attributes and Geometry
    REJECT_NULL_MISSING_KEYS = No
    MERGED -> AttributeRemover_2
    MERGED -> FeatureMerger_3 [REQUESTOR]
AttributeRemover_2
    LIST_ATTRS = childList{}
    REMOVE_ATTRS = xml_id,gml_id,xml_parent_child_pos,ID_join,plus.href,xml_matched_element,plus,minus.href,linje
    -> PointOnAreaOverlayer [AREA]
Note: NB!!!!!!!!!!!!!!!!!!!!!!!! / Swap ports Merged and / UnmergedRequestor if using / areas allowed to build
Note: Merging attributes from / areas allowed to build.
FeatureMerger_3
    SUPPLIERS_FIRST = No
    IGNORE_NULLS = No
    JOIN_KEYS = @Value(DP_Omrade.id) @Value(DP_Omrade.id) AUTO
    ATTR_CONFLICT_RES = Use Requestor
    PROCESS_DUPS = No
    ATTR_ACCUM_MODE = Merge Supplier
    MERGE_TYPE = Attributes Only
    REJECT_NULL_MISSING_KEYS = No
    MERGED -> FeatureMerger_4 [REQUESTOR]
Note: Merging with bestämmelser without geometry. / Areas not allowed to build (prickad mark) and / only "komplementbyggnad (korsmark)
FeatureMerger_4
    SUPPLIERS_FIRST = No
    IGNORE_NULLS = No
    JOIN_KEYS = @Value(omrade.xlink_href) @Value(omrade.xlink_href) AUTO
    ATTR_CONFLICT_RES = Use Requestor
    PROCESS_DUPS = Yes
    ATTR_ACCUM_MODE = Merge Supplier
    GEOM_TYPE = Build Polygons
    CONNECT_Z_MODE = First Wins
    MERGE_TYPE = Attributes and Geometry
    REJECT_NULL_MISSING_KEYS = No
    MERGED -> TestFilter_2
    UNMERGED_REQUESTOR -> TestFilter
    <REJECTED> -> FeatureMerger_4__Rejected_
Note: Splitting prickar mark and korsmark
TestFilter_2
    DEFAULT_VALUE = <UNFILTERED>
    TEST_LIST = BOOL_OP,OR,COMPOSITE_TEST,<Unused>,TEST_CLAUSE,"TEST @Value(bestammelsetyp) CONTAINS Prick",prickMark,BOOL_OP,OR,COMPOSITE_TEST,<Unused>,TEST_CLAUSE,"TEST @Value(bestammelsetyp) CONTAINS Kors",korsMark
    prickMark -> TestFilter_2_prickMark (output)
    korsMark -> TestFilter_2_korsMark (output)
TestFilter_2_prickMark (output)
TestFilter_2_korsMark (output)
TestFilter
    DEFAULT_VALUE = <UNFILTERED>
    TEST_LIST = BOOL_OP,OR,COMPOSITE_TEST,<Unused>,TEST_CLAUSE,"TEST @Value(anvandningsslag) CONTAINS gata",Gata,BOOL_OP,OR,COMPOSITE_TEST,<Unused>,TEST_CLAUSE,"TEST @Value(anvandningsslag) CONTAINS gang",Gång,BOOL_OP,OR,COMPOSITE_TEST,<Unused>,TEST_CLAUSE,"TEST @Value(anvandningsslag) CONTAINS cykel",Cykel,BOOL_OP,OR,COMPOSITE_TEST,<Unused>,TEST_CLAUSE,"TEST @Value(beteckning) CONTAINS vatten",Vatten
    Gata -> TestFilter_Gata (output)
    Gång -> TestFilter_Gång (output)
    Cykel -> TestFilter_Cykel (output)
    Vatten -> TestFilter_Vatten (output)
    <UNFILTERED> -> TestFilter__Unfiltered_ (output)
TestFilter_Gata (output)
TestFilter_Gång (output)
TestFilter_Cykel (output)
TestFilter_Vatten (output)
TestFilter__Unfiltered_ (output)
FeatureMerger_4__Rejected_: Inspector

Bookmark: Connects bestämmelser to områden
FeatureMerger_Egenskap
    SUPPLIERS_FIRST = No
    IGNORE_NULLS = No
    JOIN_KEYS = @Value(ID_join) @Value(omrade.xlink_href) AUTO
    ATTR_CONFLICT_RES = Use Requestor
    PROCESS_DUPS = Yes
    ATTR_ACCUM_MODE = Merge Supplier
    GEOM_TYPE = Build Polygons
    CONNECT_Z_MODE = First Wins
    LIST_ATTRS_TO_INCLUDE = beteckning ursprunglig uuid
    MERGE_TYPE = Attributes Only
    REJECT_NULL_MISSING_KEYS = No
    LIST_NAME = EgenskapList
    MERGED -> FeatureMerger_Anvandning [REQUESTOR]
    UNMERGED_REQUESTOR -> FeatureMerger_Anvandning [REQUESTOR]
FeatureMerger_Anvandning
    SUPPLIERS_FIRST = No
    IGNORE_NULLS = No
    JOIN_KEYS = @Value(ID_join) @Value(omrade.xlink_href) AUTO
    ATTR_CONFLICT_RES = Use Requestor
    PROCESS_DUPS = Yes
    ATTR_ACCUM_MODE = Merge Supplier
    GEOM_TYPE = Build Polygons
    CONNECT_Z_MODE = First Wins
    LIST_ATTRS_TO_INCLUDE = beteckning ursprunglig uuid
    MERGE_TYPE = Attributes Only
    REJECT_NULL_MISSING_KEYS = No
    LIST_NAME = AnvandningList_beteckning
    MERGED -> AttributeRemover
    UNMERGED_REQUESTOR -> AttributeRemover

Bookmark: Finds area where buildings are permitted
Note: To get egenskaper from points
PointOnAreaOverlayer
    CANDIDATE_LIST_ATTRS_TO_INCLUDE = beteckning ursprunglig variabel{}.DP_VarArtal.namn variabel{}.DP_VarArtal.varde variabel{}.DP_VarDatum.namn variabel{}.DP_VarDatum.varde variabel{}.DP_VarDecimaltal.namn variabel{}.DP_VarDecimaltal.varde variabel{}.DP_VarHeltal.namn variabel{}.DP_VarHeltal.varde variabel{}.DP_VarKod.namn variabel{}.DP_VarKod.varde variabel{}.DP_VarLinje.namn variabel{}.DP_VarLinje.varde variabel{}.DP_VarPunkt.namn variabel{}.DP_VarPunkt.varde variabel{}.DP_VarText.namn variabel{}.DP_VarText.varde variabel{}.owns
    POLYS_FIRST = NO
    DEAGGREGATE_INPUT = Yes
    ATTR_CONFLICT_RES = Use Original
    OV_ATTR = _overlaps
    ATTR_ACCUM_MODE = Merge Incoming
    CANDIDATE_LIST_ATTRS_TO_INCLUDE_MODE = Selected Attributes
    CANDIDATE_LIST_NAME = egenskap
    AREA -> PythonCaller_Nockhojd
Note: Finds max nockhöjd / (Other heights not considered)
PythonCaller_Nockhojd
    NEW_ATTRIBUTES = max_nock
    PYTHONSYMBOL = processFeature
    PYTHONSOURCE:
      import fme
      import fmeobjects
      # Template Function interface:
      # When using this function, make sure its name is set as the value of
      # the 'Class or Function to Process Features' transformer parameter
      def processFeature(feature):
          testString = 'gsta nockh'
          i = 0
          item = feature.getAttribute('egenskap{%i}.ursprunglig' % (i))
          maxNock = None

          while item:
              if testString in item:
                  maxNock = feature.getAttribute('egenskap{%i}.beteckning' % (i))
                  break
              i += 1
              item = feature.getAttribute('egenskap{%i}.ursprunglig' % (i))
          if maxNock:
              maxNock = maxNock.replace(",",".")
              maxNock = float(maxNock)
              feature.setAttribute('max_nock', maxNock)
    -> PythonCaller_Takvinkel
Note: Finds min and max takvinkel
PythonCaller_Takvinkel
    NEW_ATTRIBUTES = max_takvinkel min_takvinkel
    PYTHONSYMBOL = processFeature
    PYTHONSOURCE:
      import fme
      import fmeobjects
      # Template Function interface:
      # When using this function, make sure its name is set as the value of
      # the 'Class or Function to Process Features' transformer parameter
      def processFeature(feature):
          testString_1 = 'gsta taklutning'
          teststring_2 = 'taklutning i grader'
          i = 0
          item = feature.getAttribute('egenskap{%i}.ursprunglig' % (i))
          maxTakVinkel = False
          minTakVinkel = False

          while item:
              if testString_1 in item:
                  maxTakVinkel = feature.getAttribute('egenskap{%i}.beteckning' % (i))
                  break
              elif teststring_2 in item:
                  varIndex = 0
                  varItem = feature.getAttribute('egenskap{%i}.variabel{%i}.DP_VarDecimaltal.namn' % (i, varIndex))
                  while varItem:
                      if 'minvinkel' in varItem:
                          minTakVinkel = feature.getAttribute('egenskap{%i}.variabel{%i}.DP_VarDecimaltal.varde' % (i, varIndex))
                      elif 'maxvinkel' in varItem:
                          maxTakVinkel = feature.getAttribute('egenskap{%i}.variabel{%i}.DP_VarDecimaltal.varde' % (i, varIndex))
                      varIndex += 1
                      varItem = feature.getAttribute('egenskap{%i}.variabel{%i}.DP_VarDecimaltal.namn' % (i, varIndex))
              i += 1
              item = feature.getAttribute('egenskap{%i}.ursprunglig' % (i))

          if maxTakVinkel:
              #maxTakVinkel = maxTakVinkel.replace(",",".")
              #maxTakVinkel = float(maxTakVinkel)
              feature.setAttribute('max_takvinkel', maxTakVinkel)
          if minTakVinkel:
              feature.setAttribute('min_takvinkel', minTakVinkel)
    -> AttributeKeeper_2
AttributeKeeper_2
    KEEP_ATTRS = max_nock,DP_Omrade.id,max_takvinkel,byggnadshojd,min_takvinkel
    -> FeatureMerger_3 [SUPPLIER]

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

Input (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    OVERWRITE_CHOICE = Yes
    SETTYPE_PARAM = Traits From Attributes
    GQUERY:
      for $geom in //geometry
      where $geom/count(parent::geometry) = 0
      return number($geom/@fme_id)
    SRC_ATTRS = citygml_lod_name
    REMOVE_ATTRIBUTE = No
    SET -> Output (output)
Output (output)

FME custom transformer IterativeSnipper
This transformer can be used to snip a line into shorter lines by specifying a segment length or number of output lines.
Input Ports
    Input
Any feature with line geometry.
    Output Ports
    Output
Line features are output. Number of features depends on User Parameters.
    <Rejected>
Features are rejected if they do not have line geometry. The value INVALID_GEOMETRY_TYPE is stored in the fme_rejection_code attribute.
    Parameters
    Snipping Mode
Shorten to Length: Input line will be iteratively cut into lines of desired length. In this mode, a line will be cut into shorter lines until the length becomes smaller than desired length. The short segment will also be output.
Divide into Number of Lines: Input line will be snipped into a desired number of lines with equal lengths.

Parameters:
- SNIPMODE = ToLength   # Shorten to Length,ToLength%Divide into Number of Lines,ToNumber Snipping Mode
- SnipLength = 20   # Value

Input (input)
    -> GeometryFilter
Note: Filter out all geometries / except lines.
GeometryFilter
    GEOM_PORT_NAMES = Line
    BREAK_AGG = No
    LINE -> LengthCalculator
    <UNFILTERED> -> AttributeCreator
Note: Calculate length / of input line.
LengthCalculator
    DIM = 3
    LEN_ATTR = Iterative_Snipper_length
    MULT = 1
    -> Snip_Mode
Note: Determine Snipping Mode
Snip_Mode: Tester
    TEST_MODE = Automatic
    TEST_DESCRIPTION = ""
    TEST_CLAUSE = TEST $(SNIPMODE) = ToNumber
    BOOL_OP = OR
    PASSED -> ExpressionEvaluator
    FAILED -> ParameterFetcher
AttributeCreator
    ATTR_TABLE = SET_TO fme_rejection_code = INVALID_GEOMETRY_TYPE
    -> <Rejected> (output)
<Rejected> (output)
LoopINPUT (input)
    -> LengthCalculator_2
Note: Calculate length / of input line segment.
LengthCalculator_2
    DIM = 3
    LEN_ATTR = Iterative_Snipper_length
    MULT = 1
    -> Tester
Note: If line's length is less than / or equal to Snipping Distance, / send to Output. If not, snip it.
Tester
    TEST_MODE = Automatic
    TEST_DESCRIPTION = ""
    TEST_CLAUSE = TEST @Value(Iterative_Snipper_length) <= @Value(Iterative_Snipper_maxLength)
    TEST_LIST = &_length,>,&_maxLength
    BOOL_OP = OR
    PASSED -> AttributeRemover
    FAILED -> Snipper_3
Note: Cut a segment with length / of snipping distance from / the beginning of the line, / output the segment to the / output port, send the rest of the / line to the looping Output port.
Snipper_3
    MEASUREMENTTYPE = 3D
    STARTLOCATIONATTR = 0
    SNIPMODE = Distance (Value)
    ENDLOCATIONATTR = @Value(Iterative_Snipper_maxLength)
    -> AttributeRemover
    REMNANTS -> LoopINPUT (output)
Note: Clean up attributes
AttributeRemover
    REMOVE_ATTRS = Iterative_Snipper_length,Iterative_Snipper_maxLength
    -> Output (output)
Output (output)
LoopINPUT (output)

Bookmark: Determine Snipping Distance
ExpressionEvaluator
    VAL_ATTR = Iterative_Snipper_maxLength
    EXPRESSION = @Value(Iterative_Snipper_length)/@double($(SnipLength))
    ACTION = Create New Attribute
    -> Tester
ParameterFetcher
    ATTR_LIST = Iterative_Snipper_maxLength {$(SnipLength)}
    -> Tester

FME custom transformer OuterWallSegmentFinder

Parameters:
- _UUID = @Value(_uuid)   # Uuid
- INTERSECTLINE = @Value(IntersectLine)   # IntersectLine

Intersector_line_walls_Input (input)
    -> Intersector_line_walls
Note: Intersecting imaginary line with walls to / find one outer wall.
Intersector_line_walls
    SEPARATE_COLLINEAR_SEGMENTS = No
    DEAGGREGATE_INPUT = Yes
    ATTRS_ACCUM_MODE = Merge Attributes
    PERFORM_SELF_INTERSECTION = No
    OV_ATTR = _overlaps
    DUPLICATE_Z_NODES = No
    MEASURE_TYPE = Continuous
    GENERATE_LIST_DROP = NO
    SEG_ATTR = _segments
    NODE -> TestFilter
    <REJECTED> -> Intersector_line_walls__Rejected_
Intersector_line_walls__Rejected_: Inspector
Note: To find the nodes that belong to the test line
TestFilter
    DEFAULT_VALUE = <UNFILTERED>
    TEST_LIST = BOOL_OP,OR,COMPOSITE_TEST,<Unused>,TEST_CLAUSE,"TEST @Value(IntersectLine) = line",CandidateNode
    CandidateNode -> CoordinateExtractor
CoordinateExtractor
    IND = 0
    X_ATTR = _x
    Y_ATTR = _y
    MODE = Specify Coordinate
    Z_ATTR = _z
    -> Sorter
Sorter
    SORT_PARM = _x NUMERIC DESCENDING
    SORTED -> Counter
Counter
    START = 0
    SCOPE = Local
    CNT_ATTR = _count
    DOMAIN = counter
    -> Tester
Tester
    TEST_MODE = Automatic
    TEST_CLAUSE = NUM_TEST @Value(_count) = 1
    BOOL_OP = OR
    PASSED -> FeatureMerger [REQUESTOR]
FeatureMerger_Supplier (input)
    -> FeatureMerger [SUPPLIER]
Note: The merged feature / is one outer wall
FeatureMerger
    SUPPLIERS_FIRST = No
    IGNORE_NULLS = No
    JOIN_KEYS = @Value(_uuid) @Value(_uuid) AUTO
    ATTR_CONFLICT_RES = Use Requestor
    PROCESS_DUPS = No
    ATTR_ACCUM_MODE = Merge Supplier
    MERGE_TYPE = Attributes and Geometry
    REJECT_NULL_MISSING_KEYS = No
    MERGED -> FeatureMerger_Merged (output)
FeatureMerger_Merged (output)

FME custom transformer BuildingHeightCheckerNew

2DForcer_buildingImport (input)
    -> 2DForcer_3
2DForcer_buildingImport_2 (input)
    -> HullAccumulator
DevelopmentPlan_Input (input)
    -> Junction_6
Note: Only to visualilse the 16 / elevation points.
FeatureColorSetter [off]
    FILL_COLOR = 0.666667,0,0
    MODE = Fixed
    COLOR = 0.666667,0,0
    COLORED -> FeatureColorSetter_Colored
FeatureColorSetter_Colored: Inspector [off]

Bookmark: Creating the horisontal plane representing mean ground elevation.
2DForcer_3
    2D -> BoundsExtractor
    2D -> HullAccumulator_2
AttributeKeeper_4
    KEEP_ATTRS = _angle,pointElevation,wallHeightOLD,_closest_candidate_x,_candidate_angle,_distance,_closest_base_x,wallHeightNEW,_closest_candidate_y,_closest_base_y,wallOrderID,zOffset
    -> Aggregator_2
    -> PythonCaller_GroundPointLifter
Note: Calculates mean ground elevation
PythonCaller_GroundPointLifter
    NEW_ATTRIBUTES = meanElevation
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.pointList = []
              self.totElevation = 0
              self.elevOK = None

          def input(self,feature): # This function is called every time a feature is added
              if not feature.hasGeometry():
                  self.elevOK = feature.getAttribute('elevOK')
              else:
                  self.pointList.append(feature)
                  self.totElevation += feature.getAttribute('pointElevation')

          def close(self):
              if not self.elevOK:
                  print 'Elevation points are not including the highest and lowest points'
              else:
                  # Mean elevation of the ground around the building
                  meanElevation = self.totElevation*1.0/len(self.pointList)
                  # Iterating over all points and assigning z-value
                  for tempPoint in self.pointList:
                      tp = tempPoint.getGeometry()
                      tp.setZ(tempPoint.getAttribute('pointElevation'))
                      tempPoint.setGeometry(tp)
                      tempPoint.setAttribute('meanElevation', meanElevation)

                      self.pyoutput(tempPoint)
    -> PointOnAreaOverlayer_2 [POINT]
    -> FeatureColorSetter
PointOnAreaOverlayer_2
    POLYS_FIRST = No
    DEAGGREGATE_INPUT = Yes
    ATTR_CONFLICT_RES = Use Original
    OV_ATTR = _overlaps
    ATTR_ACCUM_MODE = Merge Incoming
    CANDIDATE_LIST_ATTRS_TO_INCLUDE_MODE = Selected Attributes
    AREA -> Offsetter_3
Note: Lifting the plane to the mean ground level.
Offsetter_3
    YOFF = 0
    XOFF = 0
    ZOFF = @Value(meanElevation)
    MODE = Cartesian Coordinate
    OFFSET -> FeatureColorSetter_2
    <REJECTED> -> Offsetter_3__Rejected_
FeatureColorSetter_2
    FILL_COLOR = 0.666667,0,0
    MODE = Fixed
    COLOR = 0.666667,0,0
    COLORED -> PythonCaller_heightChecker
Offsetter_3__Rejected_: Inspector

Bookmark: Finding wall lenghts
  Calculates lenght of each side of the buidling
BoundsExtractor
    XMIN = _xmin
    YMAX = _ymax
    ZMIN = _zmin
    YMIN = _ymin
    XMAX = _xmax
    ZMAX = _zmax
    -> PythonCaller_EndPointFinder
PythonCaller_EndPointFinder
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.lineList = []

          def input(self,feature): # This function is called every time a feature is added
              self.lineList.append(feature)

          def close(self):

              # Iterating over all walls to keep endpoints only
              for wallLine in self.lineList:

                  xMax = wallLine.getAttribute('_xmax')
                  xMin = wallLine.getAttribute('_xmin')
                  yMax = wallLine.getAttribute('_ymax')
                  yMin = wallLine.getAttribute('_ymin')
                  inLine = wallLine.getGeometry() # We get the geometry as a face

                  # Have not found a way of checking what geometry type the area is
                  # so using try to see if it is donut och polygon
                  try:
                      # Only outer boundary is interesting (i.e. openings not relevant)
                      pl = inLine.getOuterBoundaryAsCurve()
                  except:
                      pl = inLine.getBoundaryAsCurve()

                  pointList = pl.getPoints()

                  candidatePoints = []

                  # Looping over all points in the list keeping only those that include one
                  # boundary coordinate as candidates. Other points cannot be endpoints.
                  for tempPoint in pointList:
                      tempXYZ = tempPoint.getXYZ()
                      if xMax == tempXYZ[0] or xMin == tempXYZ[0] or yMax == tempXYZ[1] or yMin == tempXYZ[1]: # No need to check ground level points

                          candidatePoints.append(tempPoint)


                  currentLen = 0

                  for startIndex in xrange(len(candidatePoints)):
                      tempStart = candidatePoints[startIndex]
                      for endIndex in xrange(len(candidatePoints)):
                          if not startIndex == endIndex:
                              tempend = candidatePoints[1]
                              tempLen = sqrt((tempStart.getXYZ()[0]-tempend.getXYZ()[0])**2 + (tempStart.getXYZ()[1]-tempend.getXYZ()[1])**2)
                              if tempLen > currentLen:
                                  currentLen = tempLen
                                  currentStartIndex = startIndex
                                  currentEndIndex = endIndex

                  newLine = fmeobjects.FMELine([candidatePoints[currentStartIndex].getXYZ(), candidatePoints[currentEndIndex].getXYZ()])

                  wallLine.setGeometry(newLine)

                  self.pyoutput(wallLine)
    -> LengthCalculator
LengthCalculator
    DIM = 2
    LEN_ATTR = _length
    MULT = 1
    -> PythonCaller_NumberOfLineSplits

Bookmark: Creating 16 points along the building walls used to derive mean ground elevation
Note: Calculates how many points to include for / each side of the building.
PythonCaller_NumberOfLineSplits
    NEW_ATTRIBUTES = nbrLines nbrLinesDense
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.lineList = []
              self.totLen = 0
              self.nbrPoints = 16.0 # Number of points to calculate mean ground elevation

          def input(self,feature): # This function is called every time a feature is added
              self.lineList.append(feature)
              self.totLen += feature.getAttribute('_length')

          def close(self):

              lineFractions = []
              nbrPoints = []

              for wallLine in self.lineList:
                  lineFractions.append(wallLine.getAttribute('_length')/self.totLen)
                  # Number of line segments to split into
                  np = round(wallLine.getAttribute('_length')/self.totLen*self.nbrPoints)
                  nbrPoints.append(np)

                  # Creates points with a distance of half the DEM resolution to chekc that the highest and lowest
                  # elevation point is included among the points used to derived mean ground elevation.
                  npDense = round(wallLine.getAttribute('_length')/float(FME_MacroValues['DEM_resolution'])*2.0)

                  wallLine.setAttribute('nbrLines', np)
                  wallLine.setAttribute('nbrLinesDense', npDense)

                  self.pyoutput(wallLine)

              if sum(nbrPoints) != self.nbrPoints:
                  print 'WARNING!!!, number of line segments is not {}'.formatt(self.nbrPoints)
    -> IterativeSnipper
    -> IterativeSnipper_2

Bookmark: Walls -> points
  Splits the walls of the building into lines (16 to calculate mean ground elevation) and replaces the lines with a point at the startpoint of the line. Start is used to get points at the corners of the buidling.
IterativeSnipper
    SnipLength = @Value(nbrLines)
    SNIPMODE = ToNumber
    -> LengthCalculator_2
LengthCalculator_2
    DIM = 2
    LEN_ATTR = _length
    MULT = 1
    -> Tester_2
Tester_2
    TEST_MODE = Automatic
    TEST_DESCRIPTION = ""
    TEST_CLAUSE = TEST @Value(_length) > 0.1
    BOOL_OP = OR
    PASSED -> CoordinateExtractor_3
CoordinateExtractor_3
    IND = 0
    X_ATTR = _xPoint
    Y_ATTR = _yPoint
    MODE = Specify Coordinate
    Z_ATTR = _zPoint
    -> PythonCaller_PointCreator
Note: Replaces the line geometries with / a point at the start point of the line.
PythonCaller_PointCreator
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.lineList = []

          def input(self,feature):
              self.lineList.append(feature)

          def close(self):
              for l in self.lineList:
                  # Reading coords of first point of the line
                  x = l.getAttribute('_xPoint')
                  y = l.getAttribute('_yPoint')
                  z = l.getAttribute('_zPoint')

                  newPoint = fmeobjects.FMEPoint(x, y, z)
                  l.setGeometry(newPoint)
                  self.pyoutput(l)
    -> NeighborFinder [BASE]

Bookmark: Finding max and min elevation for the dense points.
  Finding max and min elevation for the dense points (distance = halv DEM resolution) to confirm that the highest and lowest points in teh DEM around the buidling are included among the 16 points used to derive mean ground elevation.
IterativeSnipper_2
    SnipLength = @Value(nbrLinesDense)
    SNIPMODE = ToNumber
    -> LengthCalculator_3
LengthCalculator_3
    DIM = 2
    LEN_ATTR = _length
    MULT = 1
    -> Tester_3
Tester_3
    TEST_MODE = Automatic
    TEST_DESCRIPTION = ""
    TEST_CLAUSE = TEST @Value(_length) > 0.1
    BOOL_OP = OR
    PASSED -> CenterPointReplacer_3
CenterPointReplacer_3
    MODE = Center Point
    POINT -> NeighborFinder_2 [BASE]
from_DEM (input)
    -> CoordinateExtractor_2
CoordinateExtractor_2
    IND = 0
    X_ATTR = _x
    Y_ATTR = _y
    MODE = Specify Coordinate
    Z_ATTR = _z
    -> AttributeCreator_4
AttributeCreator_4
    ATTR_TABLE = SET_TO pointElevation = @Value(_z)
    -> AttributeKeeper_5
AttributeKeeper_5
    KEEP_ATTRS = pointElevation
    -> NeighborFinder_2 [CANDIDATE]
NeighborFinder_2
    INSERT_VERTEX = No
    MEASURES_FROM_CANDIDATE = Yes
    ATTR_CONFLICT_RES = Use Base
    CANDIDATES_FIRST = No
    ATTR_ACCUM_MODE = Merge Candidate
    TREAT_POLYGON_AS = Lines
    MEASURE_TYPE = Continuous
    MODE = Bases and Candidates
    K = 1
    MATCHED -> AttributeKeeper_6
    <REJECTED> -> NeighborFinder__Rejected__2
AttributeKeeper_6
    KEEP_ATTRS = _angle,pointElevation,wallHeightOLD,_closest_candidate_x,_candidate_angle,_distance,_closest_base_x,wallHeightNEW,_closest_candidate_y,_closest_base_y,wallOrderID,zOffset
    -> Aggregator_3
NeighborFinder__Rejected__2: Inspector

Bookmark: Plane for height visualisation
  Creating a plane extending with the buffer amount outside teh building. Used for visualisation of mean ground surface later.
HullAccumulator_2
    HULLTYPE_PARAM = Convex ()
    3DMODE_PARAM = 2D
    HULL -> Generalizer
Generalizer
    ALG_TEXT = Douglas (Generalize)
    TOLERANCE = 1
    PRESERVE = No
    -> Bufferer
Bufferer
    CORNER_STYLE = Miter
    MITER_LIMIT = 3
    OFFSET = 2
    ANGLE = 22.5
    CAP_STYLE = None
    BUFFERED -> PointOnAreaOverlayer_2 [AREA]

Bookmark: To find in which area the building is located
HullAccumulator
    HULLTYPE_PARAM = Convex ()
    3DMODE_PARAM = 2D
    HULL -> Clipper_3 [CLIPPER]
Note: Detailed plan areas
Junction_6
    -> Clipper_3 [CLIPPEE]
Clipper_3
    MISSING_VAL_MODE = Compute
    DEFAULT_VAL = 0
    ATTR_CONFLICT_RES = Use Clippee
    ATTR_ACCUM_MODE = Merge Clipper
    CLIP_TYPE = Multiple Clippers
    CONNECT_Z_MODE = First Wins
    VAL_SOURCE = Clippee Only
    CREATE_AGGREGATES = Yes
    CLIPPED_ATTR = _clipped
    BOUNDARY_CASES = Treat as Inside
    MEASURE_TYPE = Continuous
    LINES_AS_SEGMENTS = No
    PRESERVE_CLIPPEE_EXTENTS = No
    INSIDE -> PythonCaller_heightChecker

Bookmark: Checking min and max elevation
  Checking that the highest and lowest points are included with the 16 points used to find mean ground elevation.
Aggregator_3
    ACCUM_ATTRS_NAME = Merge Incoming Attributes
    SEP = ,
    AGGREGATE_TYPE = Homogeneous Collection (If Possible)
    ORDERED = No
    LIST_ATTRS_TO_INCLUDE = pointElevation
    MODE = Geometry - Assemble One Level
    LIST_NAME = pointElevationList
    AGGREGATE -> ListRangeExtractor_2
ListRangeExtractor_2
    SRC_LIST = pointElevationList{}.pointElevation
    MIN = _minElevDense
    MAX = _maxElevDense
    -> PythonCaller_GroundPointLifter_2
Aggregator_2
    ACCUM_ATTRS_NAME = Merge Incoming Attributes
    SEP = ,
    AGGREGATE_TYPE = Homogeneous Collection (If Possible)
    ORDERED = No
    LIST_ATTRS_TO_INCLUDE = pointElevation
    MODE = Geometry - Assemble One Level
    LIST_NAME = pointElevationList
    AGGREGATE -> ListRangeExtractor
ListRangeExtractor
    SRC_LIST = pointElevationList{}.pointElevation
    MIN = _minElev
    MAX = _maxElev
    -> PythonCaller_GroundPointLifter_2
Note: Checks that the min and max / elevations are included with / the 16 points.
PythonCaller_GroundPointLifter_2
    NEW_ATTRIBUTES = elevOK
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.pointList = []
              self.pointListDense = []


          def input(self,feature): # This function is called every time a feature is added
              if feature.getAttribute('_minElevDense'):
                  self.pointListDense.append(feature)
              elif feature.getAttribute('_minElev'):
                  self.pointList.append(feature)

          def close(self):
              # Checking that min and max elevations are included in the 16 points
              minElevDiff = float(self.pointList[0].getAttribute('_minElev')) - float(self.pointListDense[0].getAttribute('_minElevDense'))
              maxElevDiff = float(self.pointList[0].getAttribute('_maxElev')) - float(self.pointListDense[0].getAttribute('_maxElevDense'))

              # Creating a new feature with the attribute elevOK with the value True if highest
              # and lowest points of teh building are included in the 16 points.
              nf = fmeobjects.FMEFeature()
              if abs(minElevDiff) < 0.01 and abs(maxElevDiff) < 0.01:
                  nf.setAttribute('elevOK', True)
              else:
                  nf.setAttribute('elevOK', False)

              self.pyoutput(nf)
    -> PythonCaller_GroundPointLifter

Bookmark: Getting elevation for the 16 points along the buildiing walls.
from_DEM_2 (input)
    -> CoordinateExtractor
CoordinateExtractor
    IND = 0
    X_ATTR = _x
    Y_ATTR = _y
    MODE = Specify Coordinate
    Z_ATTR = _z
    -> AttributeCreator_3
AttributeCreator_3
    ATTR_TABLE = SET_TO pointElevation = @Value(_z)
    -> AttributeKeeper_3
AttributeKeeper_3
    KEEP_ATTRS = pointElevation
    -> NeighborFinder [CANDIDATE]
NeighborFinder
    INSERT_VERTEX = No
    MEASURES_FROM_CANDIDATE = Yes
    ATTR_CONFLICT_RES = Use Base
    CANDIDATES_FIRST = No
    ATTR_ACCUM_MODE = Merge Candidate
    TREAT_POLYGON_AS = Lines
    MEASURE_TYPE = Continuous
    MODE = Bases and Candidates
    K = 1
    MATCHED -> AttributeKeeper_4
    <REJECTED> -> NeighborFinder__Rejected_
NeighborFinder__Rejected_: Inspector

Bookmark: Checking if the building heigth is allowed according to the development plan.
  Checks the building height against the development plan and displays the ground elevation plane. 
  If the building is too high, a horisontal plane representing max allowed building height is visualised.
Note: Checks if building height is allowed. / Adds the attribute heightOK with the / value True or False.
PythonCaller_heightChecker
    NEW_ATTRIBUTES = heightOK maxHeight
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.byggnad = []
              self.maxByggnadsHojd = None

          def input(self,feature): # This function is called every time a feature is added
              if feature.getAttribute('gml_parent_property') == 'egenskapsbestammelse':
                  self.maxByggnadsHojd = float(feature.getAttribute('byggnadshojd'))
              elif feature.getAttribute('wallHeightNEW'):
                  self.byggnad.append(feature)


          def close(self):

              for by in self.byggnad:

                  wallTop = int(by.getAttribute('wallHeightNEW'))*0.001 + float(by.getAttribute('zOffset'))

                  buildingHeight = wallTop - by.getAttribute('meanElevation')

                  # Checing if the building is lower than the allowed height with the
                  # allowed toleracne of 10 cm.
                  if buildingHeight - self.maxByggnadsHojd < 0.1:
                      by.setAttribute('heightOK', True)
                  else:
                      by.setAttribute('heightOK', False)
                      nf = by.clone()
                      geo = nf.getGeometry()
                      nl = geo.getBoundaryAsCurve()
                      np = nl.getPoints()

                      # Horisontal surface so we can take z from any point
                      newZ = np[0].getXYZ()[2] + self.maxByggnadsHojd
                      # new pointlist with coordinates lifted to max building height
                      [p.setZ(newZ) for p in np]
                      liftedXYZ = [p.getXYZ() for p in np]
                      liftedLine = fmeobjects.FMELine(liftedXYZ)
                      liftedPoly = fmeobjects.FMEPolygon(liftedLine)
                      nf.setGeometry(liftedPoly)
                      nf.setAttribute('maxHeight', 'True')
                      self.pyoutput(nf)

                  self.pyoutput(by)
    -> TestFilter_6
TestFilter_6
    DEFAULT_VALUE = <UNFILTERED>
    TEST_LIST = BOOL_OP,OR,COMPOSITE_TEST,<Unused>,TEST_CLAUSE,"TEST @Value(maxHeight) = True",maxHeight
    maxHeight -> maxHeight_if_too_high (output)
    <UNFILTERED> -> groundElevation (output)
maxHeight_if_too_high (output)
groundElevation (output)

FME custom transformer Ifc2surfacesParts

Parameters:
- IFC_UNIQUE_ID = @Value(ifc_unique_id)   # Ifc Unique Id
- IFC_PARENT_UNIQUE_ID = @Value(ifc_parent_unique_id)   # Ifc Parent Unique Id
- GML_PARENT_ID = @Value(gml_parent_id)   # Gml Parent Id
- _VZ = @Value(_vz)   # Vz

IntersectionLineCreatetor_SurfaceFootprintReplacer_Input_1 (input)
    -> IntersectionLineCreatetor [SurfaceFootprintReplacer_Input]
Note: Creating intersection line based / on footprint of slab
IntersectionLineCreatetor
    2DForcer_2_2D -> OuterWallSegmentFinder [Intersector_line_walls_Input]
NormalVectorFinder_Roof_CoordinateExtractor_Input (input)
    -> TestFilter
TestFilter
    DEFAULT_VALUE = <UNFILTERED>
    TEST_LIST = BOOL_OP,OR,COMPOSITE_TEST,<Unused>,TEST_CLAUSE,"TEST @Value(_vz) > 0",upLooking
    upLooking -> AreaCalculator
Note: SlopeCalculator
Junction_2
    -> Junction_4
BinaryEncoder_Door_Input (input)
    -> BinaryEncoder_Door
BinaryEncoder_Door
    DEST_ATTR = _parent_id
    ENCODING_TYPE = HEX
    ATTR_TO_ENCODE = ifc_parent_unique_id
    -> VariableRetriever_Door
VariableRetriever_Door
    SCOPE = Global
    VARNAME = t@Value(_parent_id)
    VALUE_ATTR = _parent_type
    -> AttributeRenamer_Door
AttributeRenamer_Door
    ATTR_TABLE:
      RENAME_SET_DEFAULT ifc_parent_unique_id > gml_parent_id
      RENAME_SET_DEFAULT ifc_unique_id > gml_id
    -> Tester_Door
Tester_Door
    TEST_MODE = Automatic
    TEST_CLAUSE = TEST @Value(_parent_type) NOT_= IfcCurtainWall
    BOOL_OP = OR
    PASSED -> IFC2CityGML_GetGrandParentId_Door [BinaryEncoder_Input]
    FAILED -> CityGMLGeometrySetter_Door
IFC2CityGML_GetGrandParentId_Door
    DEST_ATTR = gml_parent_id
    ATTR_TO_ENCODE = gml_parent_id
    -> CityGMLGeometrySetter_Door
CityGMLGeometrySetter_Door
    ROLE = opening
    GEOM = lod3MultiSurface
    -> AttributeKeeper_2
Note: Temporary to keep number af attributes down
AttributeKeeper_2
    KEEP_ATTRS = _gparent_id,Tag,ifc_parent_id,_geometry_name,_parent_id,_parent_type,gml_id
    -> Junction
    -> Junction_5
Note: FeatureMerger_Doors_Walls_Merged : Input
Junction
Note: FeatureMerger_Doors : Requestor
Junction_5
NormalVectorFinder_Walls_CoordinateExtractor_Input (input)
    -> TestFilter_Wall_Normal
TestFilter_Wall_Normal
    DEFAULT_VALUE = <UNFILTERED>
    TEST_LIST = BOOL_OP,OR,COMPOSITE_TEST,<Unused>,TEST_CLAUSE,"TEST @Value(_vz) = 0",Vertical
    Vertical -> AttributeRenamer_3
AttributeRenamer_3
    ATTR_TABLE:
      RENAME_SET_DEFAULT _vx > _vx_wall
      RENAME_SET_DEFAULT _vy > _vy_wall
      RENAME_SET_DEFAULT _vz > _vz_wall
    -> Sorter_2
Sorter_2
    SORT_PARM = ifc_unique_id NUMERIC ASCENDING
    SORTED -> Counter_2
Counter_2
    START = 0
    SCOPE = Local
    CNT_ATTR = _uuid
    DOMAIN = counter
    -> TestFilter_Walls
    -> FeatureMerger_3 [SUPPLIER]
Note: Filtering walls by building storey.
TestFilter_Walls
    DEFAULT_VALUE = <UNFILTERED>
    TEST_LIST = BOOL_OP,OR,COMPOSITE_TEST,<Unused>,TEST_CLAUSE,"TEST @Value(ifc_parent_unique_id) = 3L6rYPtbn4bvG0fUNlvutn_124",Main_building,BOOL_OP,OR,COMPOSITE_TEST,<Unused>,TEST_CLAUSE,"TEST @Value(ifc_parent_unique_id) = 3L6rYPtbn4bvG0fUNlumJV_136",Dormer
    Main_building -> AttributeRemover_2
    Dormer -> Counter_DormerID
Note: SurfaceNormalCalculator_2 : INPUT
Junction_12
AttributeRemover_2
    REMOVE_ATTRS = _vx0,_vx1,_y0,_vz0,_z0,_z2,_vz1,_vy0,_x2,_y2,_z1,_x1,_y1,_vy1,_x0
    -> WallsTo2D_Python [SurfaceFootprintReplacer_3_Input]
Note: Creating 2D lines of wall surfaces
WallsTo2D_Python
    CoordinateExtractor_End_Wall_Output -> LineDirectionChanger [AttributeCreator_2_Input]
    CoordinateExtractor_End_Wall_Output -> OuterWallSegmentFinder [Intersector_line_walls_Input]
Note: We need all lines to be in clockwise / direction.
LineDirectionChanger
    _X_END_WALL = @Value(_x_end_wall)
    _VX = @Value(_vx_wall)
    _VY = @Value(_vy_wall)
    _Y_START_WALL = @Value(_y_start_wall)
    _X_START_WALL = @Value(_x_start_wall)
    _Y_END_WALL = @Value(_y_end_wall)
    AttributeRemover_3_Output -> AttributeKeeper_4
    AttributeRemover_3_Output -> OuterWallSegmentFinder [FeatureMerger_Supplier]
OuterWallSegmentFinder
    INTERSECTLINE = @Value(IntersectLine)
    _UUID = @Value(_uuid)
    FeatureMerger_Merged -> AttributeKeeper_Input_Python
AttributeKeeper_Input_Python
    KEEP_ATTRS = _uuid
    -> AttributeCreator_6
AttributeCreator_6
    ATTR_TABLE = SET_TO outerWall = 1
    -> FeatureMerger_2 [SUPPLIER]
AttributeKeeper_4
    KEEP_ATTRS = _start_x,_uuid,_start_y,_end_x,_end_y
    -> FeatureMerger_2 [REQUESTOR]
FeatureMerger_2
    SUPPLIERS_FIRST = No
    IGNORE_NULLS = No
    JOIN_KEYS = @Value(_uuid) @Value(_uuid) AUTO
    ATTR_CONFLICT_RES = Use Requestor
    PROCESS_DUPS = No
    ATTR_ACCUM_MODE = Merge Supplier
    MERGE_TYPE = Attributes and Geometry
    REJECT_NULL_MISSING_KEYS = No
    MERGED -> PythonCaller_wallFinder
    UNMERGED_REQUESTOR -> AttributeCreator_7
AttributeCreator_7
    ATTR_TABLE = SET_TO outerWall = 0
    -> PythonCaller_wallFinder
PythonCaller_wallFinder
    NEW_ATTRIBUTES = owOrder
    PYTHONSYMBOL = FeatureProcessor
    PYTHONSOURCE:
      import fme
      import fmeobjects
      import math
      # Template Function interface:
      # When using this function, make sure its name is set as the value of
      # the 'Class or Function to Process Features' transformer parameter
      def OuterWallFinder(feature):
          pass

      class Point:
          def __init__(self, x, y):
              self.x = float(x)
              self.y = float(y)

          def dist(self, other):
              return math.sqrt((self.x-other.x)**2 + (self.y-other.y)**2)

          def __str__(self):
              return 'Point({},{})'.format(self.x,self.y)

      def owFinder(fl): # Added to run from FME

          wallOrder = 0 # Keeping track of the order of the wall segment
          eps = 10 # Deviation in mm when comparing start -> end
          epsCoords = 10 # Deviation when finding candidate points (seems same value
          # can be used for both)

          # Dictionary when the unique wall surface id is the key and the start and end
          # of the wall segment are saved as Point objects
          lineDict = dict()

          # Adding all wall segments to the dictionary
          for row in fl:
              uuid = row.getAttribute('_uuid')
              x1 = row.getAttribute('_start_x')
              x2 = row.getAttribute('_end_x')
              y1 = row.getAttribute('_start_y')
              y2 = row.getAttribute('_end_y')
              ow = row.getAttribute('outerWall')
              lineDict[uuid] = [Point(x1, y1), Point(x2, y2)]
              if ow:
                  owStart = uuid

          # For saving uuid of the wall segments. After this script is run this will
          # list all the outer wall segments
          owList = [(wallOrder, owStart)]
          startPoint = lineDict[owStart][0] # Need to keep the start point to know when last wall is found

          tempStartPoint = lineDict[owStart][0]
          tempEndPoint = lineDict[owStart][1]
          tempow = owStart # Current outer wall segment

          # This loop will run until the last outer wall is found
          while startPoint.dist(tempEndPoint) > eps:

              # finding candidate walls (connected to current wall segment)
              tempCandidates = []
              for uuid, points in lineDict.iteritems():
                  if tempEndPoint.dist(points[0]) < epsCoords:
                      tempCandidates.append(uuid)

              # Reversing current outer wall to find angles. The wall segment needs to
              # be reversed to get vectors that start at the same point, both for the
              # current wall and the candidates tested
              tempStartPoint = lineDict[tempow][1]
              tempEndPoint = lineDict[tempow][0]

              #####################################################
              # Getting angle between vectors with the dot product
              #####################################################

              # Vectors and lenght of current outer wall segment
              vx1 = tempEndPoint.x - tempStartPoint.x
              vy1 = tempEndPoint.y - tempStartPoint.y
              vx1len = tempStartPoint.dist(tempEndPoint)

              #For saving candidate wall segments as vectors.
              # index 0 = uuid
              # index 1 = tuple with x- and y-vector following candidate wall segment
              # index 2 = lenght of wall segment
              # index 3 = Clockwise angle from current wall segment
              # index 4 = True is vector is point to the right from the current wall segment
              # (looking from end -> start). From cross product.
              candidateVectors = []

              # Looping over all candidate wall segments
              for uuid in tempCandidates:
                  # End points of current wall segment
                  ts = lineDict[uuid][0]
                  te = lineDict[uuid][1]

                  # Vectors and lenght of current candidate wall segment
                  vx2 = te.x - ts.x
                  vy2 = te.y - ts.y
                  vx2len = ts.dist(te)

                  # Temporary solution since some input walls are polygons instead of lines. These have start = end and
                  # hence results in vectors with length = 0. This needs to be handled in FME.
                  # In the KTH model all outer walls are "correct" only some candidates are handled here
                  if vx2len*vx1len == 0:
                      wallSegmentAngle = 180
                      wallSegmentSide = 0
                  else:
                      # Angle
                      # NB!!!! round required below since there we special cases when math.acos was called with
                      # arguments like -1.000000000x resulting in math domain error
                      wallSegmentAngle = math.acos(round(((vx1 * vx2) + (vy1 * vy2)) / (vx1len * vx2len),4))*180/math.pi;
                      # Side true if to the right
                      wallSegmentSide = (vx1 * (te.y - tempStartPoint.y)) - (vy1 * (te.x - tempStartPoint.x)) < 0;
                  # Finding clockwise angle
                  if wallSegmentSide:
                      wallAngleCW = wallSegmentAngle
                  else:
                      wallAngleCW = 360 - wallSegmentAngle

                  candidateVectors.append((uuid,(vx2,vy2),vx2len,wallAngleCW,wallSegmentSide))

              minAngle = 360 # Starting with high to get the smallest angle
              tempUUID = ''

              for tempCandidate in candidateVectors:
                  if tempCandidate[3] < minAngle:
                      tempUUID = tempCandidate[0]
                      minAngle = tempCandidate[3]


              # Adding the found wall segment to the list and updating
              wallOrder += 1
              owList.append((wallOrder, tempUUID))
              tempStartPoint = lineDict[tempUUID][0]
              tempEndPoint = lineDict[tempUUID][1]
              tempow = tempUUID # Current outer wall segment

          return owList


      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):




              print '*'*32
              print self.featureList
              print '*'*32







              owFound = owFinder(self.featureList)

              for feature in self.featureList:
                  temp_uuid = feature.getAttribute('_uuid')
                  for wo, tu in owFound: # ow = wall order, tu = uuid
                      if not feature.getAttribute('owOrder') and tu == temp_uuid:
                          feature.setAttribute("owOrder", wo)

                  self.pyoutput(feature)
    -> TestFilter_Final_outer_wall
TestFilter_Final_outer_wall
    DEFAULT_VALUE = <UNFILTERED>
    TEST_LIST = BOOL_OP,OR,COMPOSITE_TEST,<Unused>,TEST_CLAUSE,"TEST @Value(owOrder) >= 0",outerWall
    outerWall -> FeatureMerger_3 [REQUESTOR]
Note: Merging wall surfaces with the / 2D outer wall segments to get / 3D geometry.
FeatureMerger_3
    SUPPLIERS_FIRST = No
    IGNORE_NULLS = No
    JOIN_KEYS = @Value(_uuid) @Value(_uuid) AUTO
    ATTR_CONFLICT_RES = Use Requestor
    PROCESS_DUPS = No
    ATTR_ACCUM_MODE = Merge Supplier
    MERGE_TYPE = Attributes and Geometry
    REJECT_NULL_MISSING_KEYS = No
    MERGED -> SurfaceSplitter
Note: Removing back of 2-sided wall surfaces
SurfaceSplitter
    FRONT -> PythonCaller_WallRoofAdjuster
AttributeKeeper
    KEEP_ATTRS = wallOrderID,donut
    -> Tester_Donut_walls
    -> Tester
Junction_10
    -> AttributeCreator_mainWalls
NormalVectorFinder_2_CoordinateExtractor_Input (input)
    -> AttributeRenamer
Note: Temporary solution to rename normal vectors of windows
AttributeRenamer
    ATTR_TABLE:
      RENAME_SET_DEFAULT _vx > _vx_window
      RENAME_SET_DEFAULT _vy > _vy_window
      RENAME_SET_DEFAULT _vz > _vz_window
    -> AttributeRemover
AttributeRemover
    REMOVE_ATTRS = _vy0,_vz1,_x0,_y0,_z1,_vz0,_y2,_vy1,_x1,_x2,_y1,_z0,_z2,_vx0,_vx1
    -> AttributeRenamer_Window
AttributeRenamer_Window
    ATTR_TABLE = RENAME_SET_DEFAULT ifc_unique_id > gml_id
    -> IFC2CityGML_GetGrandParentId_Window [BinaryEncoder_Input]
IFC2CityGML_GetGrandParentId_Window
    DEST_ATTR = gml_parent_id
    ATTR_TO_ENCODE = ifc_parent_unique_id
    -> CityGMLGeometrySetter_Window
CityGMLGeometrySetter_Window
    ROLE = opening
    GEOM = lod3MultiSurface
    -> AttributeKeeper_3
Note: Temporary to keep number af attributes down
AttributeKeeper_3
    KEEP_ATTRS = _gparent_id,Tag,_vz_window,Name,_geometry_name,_vx_window,_parent_id,ifc_parent_unique_id,gml_id,_vy_window
    -> UUIDGenerator_2
Note: To get unique ID for all parts
UUIDGenerator_2
    UUID_ATTR = _uuid_window
    -> Junction_3
Note: FeatureMerger_Windows : Requestor
Junction_3

Bookmark: To split into main roof and dormer
AreaCalculator
    AREA_TYPE = Plane Area
    AREA_ATTR = _areaRoof
    MULT = 1
    -> Sorter
Sorter
    SORT_PARM = _areaRoof NUMERIC DESCENDING
    SORTED -> Counter
Counter
    START = 0
    SCOPE = Local
    CNT_ATTR = _countRoofArea
    DOMAIN = counterRoofArea
    -> TestFilter_4
TestFilter_4
    DEFAULT_VALUE = <UNFILTERED>
    TEST_LIST = BOOL_OP,OR,COMPOSITE_TEST,<Unused>,TEST_CLAUSE,"TEST @Value(_countRoofArea) <= 1",mainRoof,BOOL_OP,OR,COMPOSITE_TEST,<Unused>,TEST_CLAUSE,"TEST @Value(_countRoofArea) >= 2",dormer
    mainRoof -> CoordinateExtractor_MainRoof
    mainRoof -> FeatureMerge_mainRoofTriangles [SUPPLIER]
    mainRoof -> FeatureColorSetter_mainRoof
    dormer -> CoordinateExtractor_Dormer
    dormer -> FeatureMerge_dormerTriangles [SUPPLIER]
    dormer -> FeatureColorSetter_dormerRoof

Bookmark: Dormers - Note that the part of this is hard coded.
CoordinateExtractor_Dormer
    LIST_NAME = _indices
    MODE = All Coordinates
    -> PythonCaller_TriangleSplitter_Dormer
PythonCaller_TriangleSplitter_Dormer
    NEW_ATTRIBUTES = triID count triangle
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.id = 100 #Starting with ID = 100 for dormers

          def input(self,feature):
              #self.featureList.append(feature)
              #Getting the list of coordinates
              xlist = feature.getAttribute('_indices{}.x')
              ylist = feature.getAttribute('_indices{}.y')
              zlist = feature.getAttribute('_indices{}.z')
              xlist = map(float, xlist)
              ylist = map(float,ylist)
              zlist = map(float, zlist)

              count = feature.getAttribute('_countRoofArea') # Need to add this attribute to merge with roofs later

              # Creating two triangles
              # NB!!!! "Extra" coordinates are created except first and last, hence, the indices below.
              line1Points = [(xlist[0], ylist[0], zlist[0]), (xlist[1], ylist[1], zlist[1]), (xlist[3], ylist[3], zlist[3])]
              line2Points = [(xlist[3], ylist[3], zlist[3]), (xlist[5], ylist[5], zlist[5]), (xlist[7], ylist[7], zlist[7])]
              line1 = fmeobjects.FMELine(line1Points)
              line2 = fmeobjects.FMELine(line2Points)
              poly1 = fmeobjects.FMEPolygon(line1)
              poly2 = fmeobjects.FMEPolygon(line2)

              newFeature1 = fmeobjects.FMEFeature()
              newFeature1.setGeometry(poly1)
              newFeature1.setAttribute('triID', self.id)
              newFeature1.setAttribute('count', count)
              newFeature1.setAttribute('triangle', True)
              self.pyoutput(newFeature1)

              newFeature2 = fmeobjects.FMEFeature()
              newFeature2.setGeometry(poly2)
              newFeature2.setAttribute('triID', self.id+1)
              newFeature2.setAttribute('count', count)
              newFeature2.setAttribute('triangle', True)
              self.pyoutput(newFeature2)

              self.id += 2


          def close(self):
              pass
    -> FeatureMerge_dormerTriangles [REQUESTOR]
FeatureMerge_dormerTriangles: FeatureMerger
    SUPPLIERS_FIRST = No
    IGNORE_NULLS = No
    JOIN_KEYS = @Value(count) @Value(_countRoofArea) AUTO
    ATTR_CONFLICT_RES = Use Requestor
    PROCESS_DUPS = No
    ATTR_ACCUM_MODE = Merge Supplier
    MERGE_TYPE = Attributes Only
    REJECT_NULL_MISSING_KEYS = No
    MERGED -> AttributeKeeper_RoofTriangles_2
AttributeKeeper_RoofTriangles_2
    KEEP_ATTRS = ifc_unique_id,triangle,ifc_parent_id,Description,ShapeType,ifc_parent_unique_id,ObjectType,Name,triID,GlobalId,Tag
    KEEP_LIST = _indices{} ifc_property_set{} ifc_quantity_set{}
    -> CoordinateExtractor_2
CoordinateExtractor_2
    LIST_NAME = _indices
    MODE = All Coordinates
    -> PythonCaller_WallDormerAdjuster
Counter_DormerID
    START = 100
    SCOPE = Local
    CNT_ATTR = _dormerID
    DOMAIN = counter
    -> CoordinateExtractor_3
CoordinateExtractor_3
    LIST_NAME = _coords
    MODE = All Coordinates
    -> ListRangeExtractor
ListRangeExtractor
    SRC_LIST = _coords{}.z
    MIN = _minZ
    MAX = _maxZ
    -> AttributeKeeper_5
AttributeKeeper_5
    KEEP_ATTRS = Description,ifc_unique_id,Tag,ifc_parent_id,_minZ,Axis,Box,_geometry_name,_maxZ,Name,GlobalId,Body,FootPrint,_dormerID,ifc_parent_unique_id,_uuid,ObjectType
    KEEP_LIST = ifc_property_set{} ifc_quantity_set{}
    -> TestFilter_2
TestFilter_2
    DEFAULT_VALUE = <UNFILTERED>
    TEST_LIST:
      BOOL_OP,OR,COMPOSITE_TEST,<Unused>,TEST_CLAUSE,"TEST @Value(_uuid) = 33",dormerFront,BOOL_OP,OR,COMPOSITE_TEST,<Unused>,TEST_CLAUSE,"TEST @Value(_uuid) = 29
      TEST @Value(_uuid) = 42",dormerSide
    dormerFront -> AttributeCreator
    dormerSide -> AttributeCreator_2
AttributeCreator
    ATTR_TABLE = SET_TO dormer = front
    -> PythonCaller_WallDormerAdjuster
AttributeCreator_2
    ATTR_TABLE = SET_TO dormer = side
    -> PythonCaller_WallDormerAdjuster
PythonCaller_WallDormerAdjuster
    NEW_ATTRIBUTES = wallOrderID donut
    PYTHONSYMBOL = FeatureProcessor
    PYTHONSOURCE:
      import fme
      import fmeobjects
      import math
      import numpy

      # Finds in which triangle the point p is located
      # Strictly speadking findest the closest corner point
      # since we know that the point is inside one of the triangles.
      # roofTriangle = the roof triangles in self.roofList
      # p = (x,y,z) tuple with the coordinates of the point
      def triangleFinder(roofTriangle,p):
          shortDist = 99999999
          triID = -1 # Which roof triangel the point is inside
          for triKey in roofTriangle:
              tri = roofTriangle[triKey]
              if not triKey == tri.getAttribute('triID'):
                  break # Something wrong with indices
              triGeo = tri.getGeometry()
              triPoly = triGeo.getBoundaryAsCurve()
              triPoints = triPoly.getPoints()

              for tempPoint in triPoints:
                  xyz = tempPoint.getXYZ()
                  tempDist = math.sqrt((xyz[0]-p[0])**2 + (xyz[1]-p[1])**2)
                  if tempDist < shortDist:
                      shortDist = tempDist
                      triID = triKey

          return triID


      # Calculating the offset of the z-coordinate
      # tri = current triangle
      # point = current point
      def zOffset(tri, point):
          # To get (x,y,z) tuples from the triangle
          triGeo = tri.getGeometry()
          triPoly = triGeo.getBoundaryAsCurve()
          triPoints = triPoly.getPoints()
          triPoints = triPoints[:3] # Last point is same as first point

          triXYZ = [x.getXYZ() for x in triPoints]

          b = numpy.array([[point[0]],[point[1]],[1]])
          A = numpy.array([[triXYZ[0][0], triXYZ[1][0], triXYZ[2][0]],[triXYZ[0][1], triXYZ[1][1], triXYZ[2][1]],[1,1,1]])
          coeff = numpy.linalg.solve(A, b)

          alfa = coeff[0]
          beta = coeff[1]
          gamma = coeff[2]

          zPoint = triXYZ[0][2] * alfa + triXYZ[1][2] * beta + triXYZ[2][2] * gamma

          return zPoint


      # Template Class Interface:
      # When using this class, make sure its name is set as the value of
      # the 'Class or Function to Process Features' transformer parameter
      class FeatureProcessor(object):
          def __init__(self):
              self.wallDict = {}
              self.roofDict = {}
              self.sideList = []

          def input(self,feature): # This function is called every time a feature is added

              if feature.getAttribute('triangle'):
                  self.roofDict[feature.getAttribute('triID')] = feature
              else:
                  self.wallDict[feature.getAttribute('_dormerID')] = feature
                  # The lines below gives the x,y coordinates of the side walls of the dormer.
                  # The front side of the dormer needs to be extended to these coordinates.
                  if feature.getAttribute('dormer') == 'side':
                      minZ = float(feature.getAttribute('_minZ'))
                      s = feature.getGeometry()
                      s = s.getAsArea()
                      s = s.getBoundaryAsCurve()
                      s = s.getPoints()
                      for p in s:
                          xyz = p.getXYZ()
                          if xyz[2] - minZ < 10:
                              self.sideList.append(xyz)



          def close(self):

              # Iterating over all walls to "lift" the higher coords to touch the roof
              for wallKey in self.wallDict:
                  wall = self.wallDict[wallKey]
                  wallDonut = False # To check if a geometry is donut
                  wallPolygon = False
                  wallFace = wall.getGeometry() # We get the geometry as a face
                  wallGeo = wallFace.getAsArea() # We need the "original" geometry

                  # Have not found a way of checking what geomatry type the area is
                  # so using try to see if it is donut och polygon
                  try:
                      # Only outer boundary is interesting (i.e. openings not relevant)
                      wallDonut = wallGeo.getOuterBoundaryAsCurve()
                      pointList = wallDonut.getPoints()
                  except:
                      wallPolygon = wallGeo.getBoundaryAsCurve()
                      pointList = wallPolygon.getPoints()

                  # Handling both donuts and polygons in the same fashion
                  for tempPoint in xrange(len(pointList)):
                      tempXYZ = pointList[tempPoint].getXYZ()
                      if tempXYZ[2] > 0: # No need to check ground level points

                          ###########################################################
                          # Extending the front wall of the dormer
                          # Ugly solution now..............................

                          # If front wall and coordinate is lower (minimum z).
                          #if wall.getAttribute('dormer') == 'front' and (tempXYZ[2] - float(wall.getAttribute('_minZ')) < 10):

                          # Need to move also upper point (vertical above lower outer corners of the dormer) since it is the upper
                          # point that is offset to touch the roof.
                          if wall.getAttribute('dormer') == 'front':

                              if math.sqrt((tempXYZ[0] - self.sideList[0][0])**2 + (tempXYZ[1] - self.sideList[0][1])**2) < 1000:

                                  # Updates tempXYZ since used later for finding correct triangle
                                  tempXYZ = (self.sideList[0][0], self.sideList[0][1], tempXYZ[2])

                                  print tempXYZ

                                  # Updates pointList since used for adjusting boundary later
                                  pointList[tempPoint].setX(self.sideList[0][0])
                                  pointList[tempPoint].setY(self.sideList[0][1])

                              elif math.sqrt((tempXYZ[0] - self.sideList[1][0])**2 + (tempXYZ[1] - self.sideList[1][1])**2) < 500:

                                  # Updates tempXYZ since used later for finding correct triangle
                                  tempXYZ = (self.sideList[1][0], self.sideList[1][1], tempXYZ[2])

                                  # Updates pointList since used for adjusting boundary later
                                  pointList[tempPoint].setX(self.sideList[1][0])
                                  pointList[tempPoint].setY(self.sideList[1][1])


                          # Finding which roof triangle the point is inside
                          rt = triangleFinder(self.roofDict, tempXYZ)

                          # And finding the new z-value
                          zOff = zOffset(self.roofDict[rt], tempXYZ)
                          zOff = zOff[0]

                          ###########################################################
                          # Need to check if first"last point is adjusted
                          ###########################################################

                          # To avoid adjusting z-vales that are e.g. higher part of door (since these are above ground)
                          ###########################################################
                          # Need to check roof thickness instead of hard coding
                          ###########################################################
                          # Front treated separately since sides also needs y-offset
                          if wall.getAttribute('dormer') == 'front' and zOff - tempXYZ[2] < 1000:
                              pointList[tempPoint].setX(tempXYZ[0])
                              pointList[tempPoint].setY(tempXYZ[1])
                              pointList[tempPoint].setZ(zOff)

                          # This is a quick and dirty solution that works here since sides are parallell to the x-axis
                          if wall.getAttribute('dormer') == 'side':
                              sideSlope = (4263.0-1855.0)/(6042.0-4919.0) # Hard coded from coordinates


                              if ((zOff - tempXYZ[2]) < 1000) and (tempXYZ[1] > -1860):
                                  pointList[tempPoint].setY(tempXYZ[1] - (tempXYZ[2] - zOff)*sideSlope)
                                  pointList[tempPoint].setZ(zOff)

                              elif ((zOff - tempXYZ[2]) < 1000):
                                  pointList[tempPoint].setZ(zOff)



                  # Creating a new booundary. The bounday line is treated in the
                  # same way for both polygon and donut.
                  newFeature = fmeobjects.FMEFeature()
                  newLine = fmeobjects.FMELine([x.getXYZ() for x in pointList])
                  newFeature.setAttribute('wallOrderID', int(wallKey))
                  newFeature.setAttribute('dormer', wall.getAttribute('dormer'))

                  if wallPolygon:
                      newPoly = fmeobjects.FMEPolygon(newLine)
                      newFeature.setGeometry(newPoly)
                  else:
                      wallGeo.setOuterBoundaryCurve(newLine)
                      newFeature.setGeometry(wallGeo)
                      newFeature.setAttribute('donut', 'True')

                  self.pyoutput(newFeature)
    -> Tester_Donut_dormer

Bookmark: Main roof, no modifications (except appearance)
FeatureColorSetter_mainRoof
    FILL_COLOR = 0.666667,0.666667,0
    MODE = Fixed
    COLOR = 0.666667,0.666667,0
    COLORED -> AttributeCreator_mainRoof

Bookmark: Attributes for element type
  Creating attribute to separate the element types in the building permit test.
AttributeCreator_mainRoof
    ATTR_TABLE = SET_TO type = mainRoof
    -> Offsetter
    -> Junction_2
AttributeCreator_dormerRoof
    ATTR_TABLE = SET_TO type = dormerRoof
    -> Offsetter
AttributeCreator_dormerWindow
    ATTR_TABLE = SET_TO type = dormerWindow
    -> Offsetter
AttributeCreator_dormerWall
    ATTR_TABLE = SET_TO type = dormerWall
    -> Offsetter
    -> Junction_12
    -> Junction_11
Note: TestFilter_5 : Input
Junction_11
    -> Junction_14
AttributeCreator_door
    ATTR_TABLE = SET_TO type = door
    -> Offsetter
AttributeCreator_window
    ATTR_TABLE = SET_TO type = window
    -> Offsetter
Note: PythonCaller_wallFinder_2 : Output
AttributeCreator_mainWalls
    ATTR_TABLE = SET_TO type = mainWalls
    -> Offsetter
    -> Junction_15
Note: TestFilter_5 : Input
Junction_15
    -> Junction_16

Bookmark: Creating 45 degree planes for deriving height of the facades.
  Testing if roof surfaces are steeper than 45 degree. If steeper 45-degree planes are created. If less then 45 degree, the building heigth will be calcualted as the height where the facade touch the roof.
  NB!!!!! Can only handle one roof surface.
Note: AttributeCreator_mainRoof : Output
Junction_4
    -> TestFilter_7
TestFilter_7
    DEFAULT_VALUE = <UNFILTERED>
    TEST_LIST = BOOL_OP,OR,COMPOSITE_TEST,<Unused>,TEST_CLAUSE,"TEST @Value(_countRoofArea) = 0",mainSideRoof
    mainSideRoof -> AttributeKeeper_8
2DForcer_2
    2D -> AreaOnAreaOverlayer [AREA]
PythonCaller_RoofCutter
    PYTHONSYMBOL = FeatureProcessor
    PYTHONSOURCE:
      import fme
      import fmeobjects
      from math import sqrt

      # Reading coordinates from a list of features and returning the coordinates in (x,y,z) tuples.
      def coordinateExtractor(fl):

          xyzList = [] # For keeping the (x,y,z) tuples

          for f in fl:

              geo = f.getGeometry()

              # Have not found a way of checking what geometry type the area is
              # so using try to see if it is donut och polygon and extracting
              # boundary as an FMELine feature
              try:
                  boundaryLine = geo.getOuterBoundaryAsCurve()
              except:
                  boundaryLine = geo.getBoundaryAsCurve()

              p = boundaryLine.getPoints() # List with points

              xyzList.extend([x.getXYZ() for x in p])

          return xyzList


      # Template Class Interface:
      # When using this class, make sure its name is set as the value of
      # the 'Class or Function to Process Features' transformer parameter
      class FeatureProcessor(object):
          def __init__(self):
              self.roofList = []
              self.wallList = []

          def input(self,feature):
              if feature.getAttribute('_countRoofArea') >= 0:
                  self.roofList.append(feature)
              else:
                  self.wallList.append(feature)

          def close(self):

              try:

                  wallCoords = coordinateExtractor(self.wallList)

                  for r in self.roofList:
                      geo = r.getGeometry()
                      cu = geo.getBoundaryAsCurve()
                      pl = cu.getPoints()
                      colist = [tp.getXYZ() for tp in pl]

                      # For all coordinates in current roof (only 4)
                      for ind in xrange(len(colist)):
                          co = colist[ind]
                          for wallCo in wallCoords:

                              # Since the rooftop is not vertically above the highest part of the roof the tolerance
                              # need to be high here and the new coordinate adjsuted also in x and y.
                              if (wallCo[2] > 0) and sqrt((wallCo[0]-co[0])**2 + (wallCo[1]-co[1])**2) < 1000:
                                  colist[ind] = (wallCo[0], wallCo[1], wallCo[2])

                      nl = fmeobjects.FMELine(colist)
                      np = fmeobjects.FMEPolygon(nl)
                      r.setGeometry(np)

                      self.pyoutput(r)

              except:
                  pass
    -> AttributeKeeper_9
AttributeKeeper_9
    KEEP_ATTRS = ifc_unique_id,_countRoofArea,_areaRoof
    -> CoordinateExtractor_6
    -> SlopeCalculator
SlopeCalculator
    -> CoordinateExtractor_8
CoordinateExtractor_8
    LIST_NAME = _indices
    MODE = All Coordinates
    -> ListRangeExtractor_4
ListRangeExtractor_4
    SRC_LIST = _indices{}.z
    MIN = _min_z
    MAX = _max_z
    -> TestFilter_3
TestFilter_3
    DEFAULT_VALUE = <UNFILTERED>
    TEST_LIST = BOOL_OP,OR,COMPOSITE_TEST,<Unused>,TEST_CLAUSE,"TEST @Value(_slope) <= 45",Less or equal to 45
    Less or equal to 45 -> AttributeCreator_low
    <UNFILTERED> -> AttributeCreator_high

Bookmark: Selecting roof to base height calculation on
  Now hard coded via roof area order but needs to connect to the front wall (beräkningsgrundande fasad).
AttributeKeeper_8
    KEEP_ATTRS = ifc_unique_id,_countRoofArea,_areaRoof
    -> 2DForcer_2

Bookmark: Dormer roof, no modifications (except appearance)
FeatureColorSetter_dormerRoof
    FILL_COLOR = 0.666667,0.666667,0
    MODE = Fixed
    COLOR = 0.666667,0.666667,0
    COLORED -> AttributeCreator_dormerRoof

Bookmark: Main roof - creating triangles
  Splitting roof surfaces into triangles for the interpolation to find the z-coordinate where the wall surfaces touches the roof.
CoordinateExtractor_MainRoof
    LIST_NAME = _indices
    MODE = All Coordinates
    -> PythonCaller_TriangleSplitter
PythonCaller_TriangleSplitter
    NEW_ATTRIBUTES = triID count triangle
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.id = 0

          def input(self,feature):
              #self.featureList.append(feature)
              #Getting the list of coordinates
              xlist = feature.getAttribute('_indices{}.x')
              ylist = feature.getAttribute('_indices{}.y')
              zlist = feature.getAttribute('_indices{}.z')
              xlist = map(float, xlist)
              ylist = map(float,ylist)
              zlist = map(float, zlist)

              count = feature.getAttribute('_countRoofArea') # Need to add this attribute to merge with roofs later

              # Creating two triangles
              # NB!!!! "Extra" coordinates are created except first and last, hence, the indices below.
              line1Points = [(xlist[0], ylist[0], zlist[0]), (xlist[1], ylist[1], zlist[1]), (xlist[3], ylist[3], zlist[3])]
              line2Points = [(xlist[3], ylist[3], zlist[3]), (xlist[5], ylist[5], zlist[5]), (xlist[7], ylist[7], zlist[7])]
              line1 = fmeobjects.FMELine(line1Points)
              line2 = fmeobjects.FMELine(line2Points)
              poly1 = fmeobjects.FMEPolygon(line1)
              poly2 = fmeobjects.FMEPolygon(line2)

              newFeature1 = fmeobjects.FMEFeature()
              newFeature1.setGeometry(poly1)
              newFeature1.setAttribute('triID', self.id)
              newFeature1.setAttribute('count', count)
              newFeature1.setAttribute('triangle', True)
              self.pyoutput(newFeature1)

              newFeature2 = fmeobjects.FMEFeature()
              newFeature2.setGeometry(poly2)
              newFeature2.setAttribute('triID', self.id+1)
              newFeature2.setAttribute('count', count)
              newFeature2.setAttribute('triangle', True)
              self.pyoutput(newFeature2)

              self.id += 2


          def close(self):
              pass
    -> FeatureMerge_mainRoofTriangles [REQUESTOR]
Note: Merging with original roof to get attributes back
FeatureMerge_mainRoofTriangles: FeatureMerger
    SUPPLIERS_FIRST = No
    IGNORE_NULLS = No
    JOIN_KEYS = @Value(count) @Value(_countRoofArea) AUTO
    ATTR_CONFLICT_RES = Use Requestor
    PROCESS_DUPS = No
    ATTR_ACCUM_MODE = Merge Supplier
    MERGE_TYPE = Attributes Only
    REJECT_NULL_MISSING_KEYS = No
    MERGED -> AttributeKeeper_RoofTriangles
AttributeKeeper_RoofTriangles
    KEEP_ATTRS = ifc_unique_id,triangle,ifc_parent_id,Description,ShapeType,ifc_parent_unique_id,ObjectType,Name,triID,GlobalId,Tag
    KEEP_LIST = _indices{} ifc_property_set{} ifc_quantity_set{}
    -> CoordinateExtractor
CoordinateExtractor
    LIST_NAME = _indices
    MODE = All Coordinates
    -> PythonCaller_WallRoofAdjuster

Bookmark: Finding windows and keeping walls
  Extracts the windows as holes in donuts and keeps the original walls.
Note: For windows ("up")
Note: For walls ("down")
Tester_Donut_dormer
    TEST_MODE = Automatic
    TEST_CLAUSE = TEST @Value(donut) = True
    BOOL_OP = OR
    PASSED -> DonutHoleExtractor_dormer
    PASSED -> FeatureColorSetter_dormerWalls
    FAILED -> FeatureColorSetter_dormerWalls
DonutHoleExtractor_dormer
    DEAGGREGATE_INPUT = Yes
    HOLE -> FeatureColorSetter_dormerWindows
FeatureColorSetter_dormerWindows
    FILL_COLOR = 1,1,0.498039
    MODE = Fixed
    COLOR = 1,1,0.498039
    COLORED -> AttributeCreator_dormerWindow
FeatureColorSetter_dormerWalls
    FILL_COLOR = 0.666667,0.666667,0.498039
    MODE = Fixed
    COLOR = 0.666667,0.666667,0.498039
    COLORED -> AttributeCreator_dormerWall

Bookmark: Checking if dormer shall be inclued in building height
  Adds the following attributes:
  dormerFraction - The fraction of the wall width covered by a dormer
  dormerTopX  - 
  dormerTopY  -  Coordinates of the top corner of the dormer
  dormerTopZ  -
Note: AttributeCreator_dormerWall : Output
Junction_14
    -> TestFilter_5
Note: AttributeCreator_mainWalls : Output
Junction_16
    -> TestFilter_5
TestFilter_5
    DEFAULT_VALUE = <UNFILTERED>
    TEST_LIST = BOOL_OP,OR,COMPOSITE_TEST,<Unused>,TEST_CLAUSE,"TEST @Value(wallOrderID) = 2",mainWallWithDormer,BOOL_OP,OR,COMPOSITE_TEST,<Unused>,TEST_CLAUSE,"TEST @Value(wallOrderID) = 106",mainWallDormer
    mainWallWithDormer -> AttributeCreator_3
    mainWallDormer -> CoordinateExtractor_7
CoordinateExtractor_7
    LIST_NAME = _indices
    MODE = All Coordinates
    -> AttributeCreator_4
AttributeCreator_4
    ATTR_TABLE = SET_TO isWall = False
    -> 2DForcer_3
2DForcer_3
    2D -> BoundsExtractor_3
BoundsExtractor_3
    XMIN = _xmin
    YMAX = _ymax
    YMIN = _ymin
    XMAX = _xmax
    -> AttributeCreator_5
AttributeCreator_5
    ATTR_TABLE = SET_TO dormerLen = @Evaluate(@sqrt((@Value(_xmax) - @Value(_xmin))**2 + (@Value(_ymax) - @Value(_ymin))**2))
    -> PythonCaller_dormerFraction
AttributeCreator_3
    ATTR_TABLE = SET_TO isWall = True
    -> 2DForcer_4
2DForcer_4
    2D -> BoundsExtractor_4
BoundsExtractor_4
    XMIN = _xmin
    YMAX = _ymax
    YMIN = _ymin
    XMAX = _xmax
    -> AttributeCreator_8
AttributeCreator_8
    ATTR_TABLE = SET_TO wallLen = @Evaluate(@sqrt((@Value(_xmax) - @Value(_xmin))**2 + (@Value(_ymax) - @Value(_ymin))**2))
    -> PythonCaller_dormerFraction
PythonCaller_dormerFraction
    NEW_ATTRIBUTES = dormerFraction dormerTopX dormerTopY dormerTopZ
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.wall = []
              self.dormer = []

          def input(self,feature):
              if feature.getAttribute('wallLen'):
                  self.wall.append(feature)
              elif feature.getAttribute('dormerLen'):
                  self.dormer.append(feature)


          def close(self):
              # The fraction of the wall len covered by the dormer
              dormerFraction = self.dormer[0].getAttribute('dormerLen')*1.0/self.wall[0].getAttribute('wallLen')

              xl = self.dormer[0].getAttribute('_indices{}.x')
              yl = self.dormer[0].getAttribute('_indices{}.y')
              zl = self.dormer[0].getAttribute('_indices{}.z')

              zm = round(float(max(zl)))

              idx = 0
              while not round(float(zl[idx])) == zm:
                  idx += 1


              self.wall[0].setAttribute('dormerFraction', dormerFraction)
              self.wall[0].setAttribute('dormerTopX', xl[idx])
              self.wall[0].setAttribute('dormerTopY', yl[idx])
              self.wall[0].setAttribute('dormerTopZ', zl[idx])

              self.pyoutput(self.wall[0])
    -> PythonCaller_WallRoofAdjuster_2

Bookmark: Connecting walls to roof surface
  "Lifting" the upper edge of the wall surfaces to touch the upper roof surface.
  NB! It only gives correct result when the roof-ridge is vertically above the edge of the wall connected to the roof.
Note: Finding where the wall corners touch / the roof (Z-direction) and adjusting / wall surfaces to touoch the roof.
PythonCaller_WallRoofAdjuster
    NEW_ATTRIBUTES = wallOrderID donut
    PYTHONSYMBOL = FeatureProcessor
    PYTHONSOURCE:
      import fme
      import fmeobjects
      import math
      import numpy

      # Finds in which triangle the point p is located
      # Strictly speadking findest the closest corner point
      # since we know that the point is inside one of the triangles.
      # roofTriangle = the roof triangles in self.roofList
      # p = (x,y,z) tuple with the coordinates of the point
      def triangleFinder(roofTriangle,p):
          shortDist = 99999999
          triID = -1 # Which roof triangel the point is inside
          for triKey in roofTriangle:
              tri = roofTriangle[triKey]
              if not triKey == tri.getAttribute('triID'):
                  break # Something wrong with indices
              triGeo = tri.getGeometry()
              triPoly = triGeo.getBoundaryAsCurve()
              triPoints = triPoly.getPoints()

              for tempPoint in triPoints:
                  xyz = tempPoint.getXYZ()
                  tempDist = math.sqrt((xyz[0]-p[0])**2 + (xyz[1]-p[1])**2)
                  if tempDist < shortDist:
                      shortDist = tempDist
                      triID = triKey

          return triID



      # Calculating the offset of the z-coordinate
      # tri = current triangle
      # point = current point
      def zOffset(tri, point):
          # To get (x,y,z) tuples from the triangle
          triGeo = tri.getGeometry()
          triPoly = triGeo.getBoundaryAsCurve()
          triPoints = triPoly.getPoints()
          triPoints = triPoints[:3] # Last point is same as first point

          triXYZ = [x.getXYZ() for x in triPoints]

          b = numpy.array([[point[0]],[point[1]],[1]])
          A = numpy.array([[triXYZ[0][0], triXYZ[1][0], triXYZ[2][0]],[triXYZ[0][1], triXYZ[1][1], triXYZ[2][1]],[1,1,1]])
          coeff = numpy.linalg.solve(A, b)

          alfa = coeff[0]
          beta = coeff[1]
          gamma = coeff[2]

          zPoint = triXYZ[0][2] * alfa + triXYZ[1][2] * beta + triXYZ[2][2] * gamma

          return zPoint


      # Template Class Interface:
      # When using this class, make sure its name is set as the value of
      # the 'Class or Function to Process Features' transformer parameter
      class FeatureProcessor(object):
          def __init__(self):
              self.wallDict = {}
              self.roofDict = {}

          def input(self,feature): # This function is called every time a feature is added

              if feature.getAttribute('triangle'):
                  self.roofDict[feature.getAttribute('triID')] = feature
              else:
                  self.wallDict[feature.getAttribute('owOrder')] = feature

          def close(self):

              # Iterating over all walls to "lift" the higher coords to touch the roof
              for wallKey in self.wallDict:
                  wall = self.wallDict[wallKey]
                  wallDonut = False # To check if a geometry is donut
                  wallPolygon = False
                  wallFace = wall.getGeometry() # We get the geometry as a face
                  wallGeo = wallFace.getAsArea() # We need the "original" geometry

                  # Have not found a way of checking what geometry type the area is
                  # so using try to see if it is donut och polygon
                  try:
                      # Only outer boundary is interesting (i.e. openings not relevant)
                      wallDonut = wallGeo.getOuterBoundaryAsCurve()
                      pointList = wallDonut.getPoints()
                  except:
                      wallPolygon = wallGeo.getBoundaryAsCurve()
                      pointList = wallPolygon.getPoints()

                  # Handling both donuts and polygons in the same fashion
                  for tempPoint in xrange(len(pointList)):
                      tempXYZ = pointList[tempPoint].getXYZ()
                      if tempXYZ[2] > 0: # No ned to check ground level points

                          # Finding which roof triangle the point is inside
                          rt = triangleFinder(self.roofDict, tempXYZ)

                          # And finding the new z-value
                          zOff = zOffset(self.roofDict[rt], tempXYZ)

                          ###########################################################
                          # Need to check if first"last point is adjusted
                          ###########################################################

                          # To avoid adjusting z-vales that are e.g. higher part of door (since these are above ground)
                          ###########################################################
                          # Need to check roof thickness instead of hard coding
                          ###########################################################
                          if zOff - tempXYZ[2] < 1000:
                              pointList[tempPoint].setZ(zOff)


                  # Creating a new booundary. The boundary line is treated in the
                  # same way for both polygon and donut.
                  newFeature = fmeobjects.FMEFeature()
                  newLine = fmeobjects.FMELine([x.getXYZ() for x in pointList])
                  newFeature.setAttribute('wallOrderID', int(wallKey))

                  if wallPolygon:
                      newPoly = fmeobjects.FMEPolygon(newLine)
                      newFeature.setGeometry(newPoly)
                  else:
                      wallGeo.setOuterBoundaryCurve(newLine)
                      newFeature.setGeometry(wallGeo)
                      newFeature.setAttribute('donut', 'True')

                  self.pyoutput(newFeature)
    -> AttributeKeeper

Bookmark: Finding the door
  Extracts the geometry of the wall by rotating the wall surface with door and clipping the convex hull of the wall with the original wall, i.e. the door will be the remainder. Then rotating the door back.
Tester
    TEST_MODE = Automatic
    TEST_CLAUSE = TEST @Value(wallOrderID) = 4
    BOOL_OP = OR
    PASSED -> 3DRotator
3DRotator
    XDIR = 0
    YORIG = 0
    AXIS_CHOICE = Custom Axis
    ZORIG = 0
    ZDIR = 0
    ANGLE = 90
    YDIR = 1
    XORIG = 0
    ROTATED -> HullReplacer_2
    ROTATED -> Clipper [CLIPPER]
HullReplacer_2
    HULLTYPE_PARAM = Convex ()
    3DMODE_PARAM = Automatic
    HULL -> Clipper [CLIPPEE]
Clipper
    MISSING_VAL_MODE = Compute
    DEFAULT_VAL = 0
    ATTR_CONFLICT_RES = Use Clippee
    ATTR_ACCUM_MODE = Merge Clipper
    CLIP_TYPE = Multiple Clippers
    CONNECT_Z_MODE = First Wins
    VAL_SOURCE = Clippee Only
    CREATE_AGGREGATES = Yes
    CLIPPED_ATTR = _clipped
    BOUNDARY_CASES = Treat as Inside
    MEASURE_TYPE = Continuous
    LINES_AS_SEGMENTS = No
    PRESERVE_CLIPPEE_EXTENTS = No
    OUTSIDE -> 3DRotator_2
3DRotator_2
    AXIS_CHOICE = Y Axis
    ANGLE = 270
    ROTATED -> FeatureColorSetter_door
FeatureColorSetter_door
    FILL_COLOR = 0.666667,0.333333,0
    MODE = Fixed
    COLOR = 0.666667,0.333333,0
    COLORED -> AttributeCreator_door
    COLORED -> BoundsExtractor_2

Bookmark: To handle the wall with door
BoundsExtractor_2
    XMIN = _xmin
    -> 3DRotator_7
3DRotator_7
    XDIR = 0
    YORIG = 0
    AXIS_CHOICE = Custom Axis
    ZORIG = 0
    ZDIR = 0
    ANGLE = 90
    YDIR = 1
    XORIG = @Value(_xmin)
    ROTATED -> Clipper_2 [CLIPPER]
Tester_2
    TEST_MODE = Automatic
    TEST_CLAUSE = TEST @Value(wallOrderID) = 4
    BOOL_OP = OR
    PASSED -> Clipper_2 [CLIPPEE]
    FAILED -> 3DRotator_6
Clipper_2
    MISSING_VAL_MODE = Compute
    DEFAULT_VAL = 0
    ATTR_CONFLICT_RES = Use Clippee
    ATTR_ACCUM_MODE = Merge Clipper
    CLIP_TYPE = Multiple Clippers
    CONNECT_Z_MODE = First Wins
    VAL_SOURCE = Clippee Only
    CREATE_AGGREGATES = Yes
    CLIPPED_ATTR = _clipped
    BOUNDARY_CASES = Treat as Inside
    MEASURE_TYPE = Continuous
    LINES_AS_SEGMENTS = No
    PRESERVE_CLIPPEE_EXTENTS = No
    OUTSIDE -> 3DRotator_6

Bookmark: Finding windows and keeping walls
  Extracts the windows as holes in donuts and keeps the original walls.
Note: For windows ("up")
Note: For walls ("down")
Tester_Donut_walls
    TEST_MODE = Automatic
    TEST_CLAUSE = TEST @Value(donut) = True
    BOOL_OP = OR
    PASSED -> DonutHoleExtractor_walls
    PASSED -> SurfaceNormalCalculator
    FAILED -> SurfaceNormalCalculator
DonutHoleExtractor_walls
    DEAGGREGATE_INPUT = Yes
    HOLE -> FeatureColorSetter_windows
FeatureColorSetter_windows
    FILL_COLOR = 1,1,0.498039
    MODE = Fixed
    COLOR = 1,1,0.498039
    COLORED -> AttributeCreator_window

Bookmark: To get one wall per side.
  NB!!!!!!!!!!!!!!
  Check if this gives correct result for other buildings!
  Here assumed that walls are either vertical or horisontal (which seems common).
  If problems here, connect the input to this bookmark (Tester_Donut_Walls) directly
  to output of this bookmark (AttributeCreator_mainWalls)
SurfaceNormalCalculator
    Ok -> Aggregator
Aggregator
    ACCUM_ATTRS_NAME = Merge Incoming Attributes
    SEP = ,
    AGGREGATE_TYPE = Homogeneous Collection (If Possible)
    ORDERED = No
    GROUP_BY = normalY normalX
    MODE = Geometry - Assemble One Level
    AGGREGATE -> BoundsExtractor
    AGGREGATE -> Junction_7
Note: PythonCaller_wallExtender : Input
Junction_7
    -> Junction_8
Note: Aggregator : Aggregate
Junction_8
    -> PythonCaller_wallExtender
BoundsExtractor
    XMIN = _xmin
    YMAX = _ymax
    YMIN = _ymin
    XMAX = _xmax
    -> TestFilter_6
TestFilter_6
    DEFAULT_VALUE = <UNFILTERED>
    TEST_LIST = BOOL_OP,OR,COMPOSITE_TEST,<Unused>,TEST_CLAUSE,"TEST @Evaluate(@Value(_xmax)-@Value(_xmin)) < 0.1",Vertical,BOOL_OP,OR,COMPOSITE_TEST,<Unused>,TEST_CLAUSE,"TEST @Evaluate(@Value(_ymax)-@Value(_ymin)) < 0.1",Horisontal
    Vertical -> 3DRotator_3
    Horisontal -> 3DRotator_4
3DRotator_3
    XDIR = 0
    YORIG = 0
    AXIS_CHOICE = Custom Axis
    ZORIG = 0
    ZDIR = 0
    ANGLE = 90
    YDIR = 1
    XORIG = @Value(_xmin)
    ROTATED -> HullReplacer_4
HullReplacer_4
    HULLTYPE_PARAM = Convex ()
    3DMODE_PARAM = Automatic
    HULL -> Tester_2
3DRotator_6
    XDIR = 0
    YORIG = 0
    AXIS_CHOICE = Custom Axis
    ZORIG = 0
    ZDIR = 0
    ANGLE = 270
    YDIR = 1
    XORIG = @Value(_xmin)
    ROTATED -> PythonCaller_boundsReplacer
3DRotator_4
    XDIR = 1
    YORIG = @Value(_ymin)
    AXIS_CHOICE = Custom Axis
    ZORIG = 0
    ZDIR = 0
    ANGLE = 90
    YDIR = 0
    XORIG = 0
    ROTATED -> HullReplacer_3
HullReplacer_3
    HULLTYPE_PARAM = Convex ()
    3DMODE_PARAM = Automatic
    HULL -> 3DRotator_5
3DRotator_5
    XDIR = 1
    YORIG = @Value(_ymin)
    AXIS_CHOICE = Custom Axis
    ZORIG = 0
    ZDIR = 0
    ANGLE = 270
    YDIR = 0
    XORIG = 0
    ROTATED -> PythonCaller_boundsReplacer
PythonCaller_boundsReplacer
    NEW_ATTRIBUTES = outerBoundary
    PYTHONSYMBOL = FeatureProcessor
    PYTHONSOURCE:
      import fme
      import fmeobjects
      import math

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):

              for f in self.featureList:

                  f.setGeometry(f.getGeometry().getBoundaryAsCurve())
                  f.setAttribute('outerBoundary', True)

                  self.pyoutput(f)
    -> AttributeKeeper_7
AttributeKeeper_7
    KEEP_ATTRS = wallOrderID,outerBoundary
    -> PythonCaller_wallExtender
Note: Creates one wall surface per side by taking the / geometry from boundary line and extending the / polygons or donuts.
PythonCaller_wallExtender
    PYTHONSYMBOL = FeatureProcessor
    PYTHONSOURCE:
      import fme
      import fmeobjects
      import math

      # Template Class Interface:
      # When using this class, make sure its name is set as the value of
      # the 'Class or Function to Process Features' transformer parameter
      class FeatureProcessor(object):
          def __init__(self):
              self.polyDict = {}
              self.boundaryDict = {}

          def input(self,feature): # This function is called every time a feature is added
              if feature.getAttribute('outerBoundary'):
                  self.boundaryDict[feature.getAttribute('wallOrderID')] = feature
              else:
                  self.polyDict[feature.getAttribute('wallOrderID')] = feature


          def close(self):
              for key in self.polyDict:
                  wall = self.polyDict[key]
                  wallGeo = wall.getGeometry()
                  wallGeo = wallGeo.getPartAt(0)
                  boundary = self.boundaryDict[key]
                  boundaryGeo = boundary.getGeometry()
                  poly = True # If polygon

                  # Have not found a way of checking what geometry type the area is
                  # so using try to see if it is donut och polygon
                  try:
                      boundaryLine = wallGeo.getOuterBoundaryAsCurve()
                      poly = False
                  except:
                      boundaryLine = wallGeo.getBoundaryAsCurve()

                  if poly:
                      newPoly = fmeobjects.FMEPolygon(boundaryGeo)
                      wall.setGeometry(newPoly)
                  else:
                      wallGeo.setOuterBoundaryCurve(boundaryGeo)
                      wall.setGeometry(wallGeo)

                  self.pyoutput(wall)
    -> AttributeRenamer_2
FeatureColorSetter_walls_2
    FILL_COLOR = 0.666667,0.666667,0.498039
    MODE = Fixed
    COLOR = 0.666667,0.666667,0.498039
    COLORED -> Junction_9
    COLORED -> Junction_6
Note: AttributeCreator_mainWalls : Input
Junction_9
    -> Junction_10
Note: 2DForcer : Input
Junction_6
    -> Junction_13

Bookmark: Orientering reversed walls
  In the step where one wall per side is created (PythonCaller_wallExtender) some walls get reveresed orientation. These walls are corrected by comparing the surface normal from before and after the wallExtender and reversing the walls that have wrong orientation, i.e. after this all walls haev a surface normal pointing out of the house.
AttributeRenamer_2
    ATTR_TABLE:
      RENAME_SET_DEFAULT normalX > normX_org
      RENAME_SET_DEFAULT normalY > normY_org
      RENAME_SET_DEFAULT normalZ > normZ_org
    -> SurfaceNormalCalculator_2
SurfaceNormalCalculator_2
    Ok -> AttributeCreator_9
AttributeCreator_9
    ATTR_TABLE:
      SET_TO normDiffX = @Evaluate(@abs(@Value(normX_org)-@Value(normalX)))
      SET_TO normDiffY = @Evaluate(@abs(@Value(normY_org)-@Value(normalY)))
    -> TestFilter_9
TestFilter_9
    DEFAULT_VALUE = <UNFILTERED>
    TEST_LIST:
      BOOL_OP,AND,COMPOSITE_TEST,<Unused>,TEST_CLAUSE,"TEST @Value(normDiffX) < 0.1
      TEST @Value(normDiffY) < 0.1",correct
    correct -> CoordinateExtractor_5
    <UNFILTERED> -> Orientor
Orientor
    KIND = REVERSE
    FLIP_APPEARANCES_CHOICE = Yes
    ORIENTED -> CoordinateExtractor_5

Bookmark: Building height for each side (Almost hard coded....)
  The height of the intersection line between the faade plane and the 45 degree plane touching the highest part of teh roof is given as an attribute.
  WallHeightNEW and WallHeightOLD are according to the new suggested method and the current method in Sweden.
  When the building heigth is calculated later only the difference between the ground plane representing the mean ground elevation and the heigth given here (with an offset to get the heigth over the geoid) is calculated.
CoordinateExtractor_5
    IND = 0
    X_ATTR = _x
    Y_ATTR = _y
    LIST_NAME = _indices
    MODE = All Coordinates
    Z_ATTR = _z
    -> ListRangeExtractor_2
ListRangeExtractor_2
    SRC_LIST = _indices{}.z
    MIN = _minZvalue
    MAX = _maxZvalue
    -> PythonCaller_wallHeight_TEMP
PythonCaller_wallHeight_TEMP
    NEW_ATTRIBUTES = wallHeightNEW wallHeightOLD
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.featureDict = {}

          def input(self,feature):
              self.featureDict[feature.getAttribute('wallOrderID')] = feature

          def close(self):

              for wallKey in self.featureDict:

                  if wallKey == 2 or wallKey == 6:
                      wh = self.featureDict[wallKey].getAttribute('_maxZvalue')
                  else:
                      wh = self.featureDict[6].getAttribute('_maxZvalue')


                  self.featureDict[wallKey].setAttribute('wallHeightNEW', wh)
                  self.featureDict[wallKey].setAttribute('wallHeightOLD', self.featureDict[wallKey].getAttribute('_maxZvalue'))

                  self.pyoutput(self.featureDict[wallKey])
              else:
                  pass
    -> AttributeRounder_wallHeights
AttributeRounder_wallHeights
    PLACES = 0
    ROUND_TYPE = Nearest
    SRC_ATTRS = wallHeightNEW wallHeightOLD
    -> FeatureColorSetter_walls_2

Bookmark: To get SWEREF99 13 30
  Moving (to get origin in LL corner) and scaling to get meters.
  Setting reference system to SWEREF 99 13 30
  Removing all attributes (should adjust later to map and keep)
Offsetter
    YOFF = 6536
    XOFF = 9207
    ZOFF = 0
    MODE = Cartesian Coordinate
    OFFSET -> Scaler
Scaler
    ZSCALE = 0.001
    SCALE_ORIGIN = 0,0
    YSCALE = 0.001
    XSCALE = 0.001
    RASTER_SCALING = Extents
    TEXT_LOC_ONLY = Location and Size
    SCALED -> CoordinateSystemSetter
CoordinateSystemSetter
    COORDSYS = EPSG:3008
    -> AttributeKeeper_6
AttributeKeeper_6
    KEEP_ATTRS = wallHeightNEW,type,wallOrderID,wallHeightOLD
    -> AttributeKeeper_6_Output (output)
AttributeKeeper_6_Output (output)

Bookmark: Finding x,y of corners, Wall footprint
Note: FeatureColorSetter_walls_2 : Colored
Junction_13
    -> 2DForcer
    -> PythonCaller_RoofCutter
2DForcer
    2D -> HullAccumulator
HullAccumulator
    HULLTYPE_PARAM = Convex ()
    3DMODE_PARAM = 2D
    HULL -> Generalizer
Note: To remove points that are / not corner points.
Generalizer
    ALG_TEXT = Douglas (Generalize)
    TOLERANCE = 10
    PRESERVE = No
    -> CoordinateExtractor_4
CoordinateExtractor_4
    IND = 0
    X_ATTR = _x
    Y_ATTR = _y
    LIST_NAME = _indices
    MODE = All Coordinates
    Z_ATTR = _z
    -> AreaOnAreaOverlayer [AREA]

Bookmark: To get the part of the roofs inside the outer walls
AreaOnAreaOverlayer
    CONNECT_Z_MODE = First Wins
    DEAGGREGATE_INPUT = Yes
    ACCUM_ATTRS_NAME = Merge Incoming Attributes
    OVC_ATTR = _overlaps
    AREA -> TestFilter_8
TestFilter_8
    DEFAULT_VALUE = <UNFILTERED>
    TEST_LIST = BOOL_OP,OR,COMPOSITE_TEST,<Unused>,TEST_CLAUSE,"TEST @Value(_overlaps) > 1",mainRoof
    mainRoof -> PythonCaller_RoofCutter

Bookmark: Adding attribute to state if the roof surface should touch the higher or lower part of the roof
AttributeCreator_low
    ATTR_TABLE = SET_TO roofTouch = low
    -> PythonCaller_45degreePlane_lifter
AttributeCreator_high
    ATTR_TABLE = SET_TO roofTouch = high
    -> PythonCaller_45degreePlane_lifter

Bookmark: Creating 45 degree roof surface
CoordinateExtractor_6
    LIST_NAME = _indices
    MODE = All Coordinates
    -> ListRangeExtractor_3
    -> PythonCaller_Roof45degree
ListRangeExtractor_3
    SRC_LIST = _indices{}.z
    MIN = _min_z
    MAX = _max_z
    -> Aggregator_3
Aggregator_3
    ACCUM_ATTRS_NAME = Use Attributes From One Feature
    SEP = ,
    AGGREGATE_TYPE = Homogeneous Collection (If Possible)
    ORDERED = No
    LIST_ATTRS_TO_INCLUDE = _max_z _min_z
    MODE = Geometry - Assemble One Level
    LIST_NAME = z_list
    AGGREGATE -> AttributeCreator_12
AttributeCreator_12
    ATTR_TABLE = SET_TO aggr = 1
    -> PythonCaller_Roof45degree
PythonCaller_Roof45degree
    NEW_ATTRIBUTES = 45plane
    PYTHONSYMBOL = FeatureProcessor
    PYTHONSOURCE:
      import fme
      import fmeobjects
      from math import sqrt
      from math import tan
      from math import pi

      # Template Class Interface:
      # When using this class, make sure its name is set as the value of
      # the 'Class or Function to Process Features' transformer parameter
      class FeatureProcessor(object):
          def __init__(self):
              self.featureList = []
              self.high = []
              self.low = []

          def input(self,feature):
              if feature.getAttribute('aggr'):
                  self.high = feature.getAttribute('_max_z')
                  self.low = feature.getAttribute('_min_z')
              else:
                  self.featureList.append(feature)

          def close(self):
              try:
                  for r in self.featureList:

                      geo = r.getGeometry()
                      cu = geo.getBoundaryAsCurve()
                      pl = cu.getPoints()
                      colist = [tp.getXYZ() for tp in pl]
                      shortSeg = 999999 # To find length of shortest line seg
                      # Range -3 since we want the distance between current and next coordinate and the last and first coordinate is the same. So
                      # with -3 there is no need to check if the distance is zero.
                      for i in range(len(colist)-3):
                          dist = round(sqrt((colist[i][0]-colist[i+1][0])**2 + (colist[i][1]-colist[i+1][1])**2))
                          if dist < shortSeg:
                              shortSeg = dist

                      # New point list to get plane with 45 degree slope
                      newpl = []
                      for pnt in pl:
                          co = pnt.getXYZ()
                          # z offset for higher points will be same as horisontal dist to get 45 degree plan
                          if round(co[2]) == round(float(self.high)):
                              co = (co[0], co[1], shortSeg)
                          else:
                              co = (co[0], co[1], 0)
                          newpl.append(co)

                      nl = fmeobjects.FMELine(newpl)
                      np = fmeobjects.FMEPolygon(nl)
                      r.setGeometry(np)

                      r.setAttribute('45plane', True)

                      self.pyoutput(r)
              except:
                  pass
    -> PythonCaller_45degreePlane_lifter

Bookmark: Placing 45 degree plane at correct level
  Lifts the 45 degree plane to touch the top of the facade if roof angle <= 45 degrees
  Lifts the 45 degree plane to touch the top of the roof ridge if roof angle <= 45 degrees
  The minimum z-value of the 45 degree plane after placement is the intersection between 45 degree plane and facade plane.
PythonCaller_45degreePlane_lifter
    PYTHONSYMBOL = FeatureProcessor
    PYTHONSOURCE:
      import fme
      import fmeobjects
      from math import sqrt
      from math import tan
      from math import pi

      # Template Class Interface:
      # When using this class, make sure its name is set as the value of
      # the 'Class or Function to Process Features' transformer parameter
      class FeatureProcessor(object):
          def __init__(self):
              self.plane45 = []
              self.highAngle = False # If roof angle > 45 i.e. 45 degree plane touching roof top
              self.high = None
              self.low = None

          def input(self,feature):
              if feature.getAttribute('roofTouch'):
                  self.highAngle = feature.getAttribute('roofTouch') == 'high'
                  self.high = feature.getAttribute('_max_z')
                  self.low = feature.getAttribute('_min_z')
              elif feature.getAttribute('45plane'):
                  self.plane45.append(feature)

          def close(self):
              for r in self.plane45:

                  geo = r.getGeometry()
                  cu = geo.getBoundaryAsCurve()
                  pl = cu.getPoints()
                  colist = [tp.getXYZ() for tp in pl]
                  newpl = []

                  # If roof less than 45 degrees
                  if self.highAngle:
                      zOffset = float(self.high)
                  else:
                      zOffset = float(self.low)

                  for pnt in pl:
                      co = pnt.getXYZ()
                      # "Lifting" all points so lower side of plane is touching the top of the facade
                      co = (co[0], co[1], co[2] + zOffset)
                      newpl.append(co)

                  nl = fmeobjects.FMELine(newpl)
                  np = fmeobjects.FMEPolygon(nl)
                  r.setGeometry(np)

                  self.pyoutput(r)
    -> AttributeKeeper_45degreePlane

Bookmark: Lifting the 45 degree plane to touch the top of the dormer if dormer shall be included in building height
  Lifts the 45 degree plane to touch the top of the dormer (note dormer wall not roof edge of dormer)
  The minimum z-value of the 45 degree plane after placement is the intersection between 45 degree plane and facade plane.
AttributeKeeper_45degreePlane
    KEEP_ATTRS = ifc_unique_id,_countRoofArea
    -> CoordinateExtractor_45degreePlane
    -> PythonCaller_WallRoofAdjuster_2
CoordinateExtractor_45degreePlane
    LIST_NAME = _indices
    MODE = All Coordinates
    -> PythonCaller_TriangleSplitter_45degreePlane
PythonCaller_TriangleSplitter_45degreePlane
    NEW_ATTRIBUTES = triID count triangle
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.id = 0

          def input(self,feature):
              #self.featureList.append(feature)
              #Getting the list of coordinates
              xlist = feature.getAttribute('_indices{}.x')
              ylist = feature.getAttribute('_indices{}.y')
              zlist = feature.getAttribute('_indices{}.z')
              xlist = map(float, xlist)
              ylist = map(float,ylist)
              zlist = map(float, zlist)

              count = feature.getAttribute('_countRoofArea') # Need to add this attribute to merge with roofs later

              # Creating two triangles
              line1Points = [(xlist[0], ylist[0], zlist[0]), (xlist[1], ylist[1], zlist[1]), (xlist[2], ylist[2], zlist[2])]
              line2Points = [(xlist[2], ylist[2], zlist[2]), (xlist[3], ylist[3], zlist[3]), (xlist[4], ylist[4], zlist[4])]
              line1 = fmeobjects.FMELine(line1Points)
              line2 = fmeobjects.FMELine(line2Points)
              poly1 = fmeobjects.FMEPolygon(line1)
              poly2 = fmeobjects.FMEPolygon(line2)

              newFeature1 = fmeobjects.FMEFeature()
              newFeature1.setGeometry(poly1)
              newFeature1.setAttribute('triID', self.id)
              newFeature1.setAttribute('count', count)
              newFeature1.setAttribute('triangle', True)
              self.pyoutput(newFeature1)

              newFeature2 = fmeobjects.FMEFeature()
              newFeature2.setGeometry(poly2)
              newFeature2.setAttribute('triID', self.id+1)
              newFeature2.setAttribute('count', count)
              newFeature2.setAttribute('triangle', True)
              self.pyoutput(newFeature2)

              self.id += 2


          def close(self):
              pass
    -> PythonCaller_WallRoofAdjuster_2
Note: NB!!!! No output if dormer is lexx than 30% of wll width
PythonCaller_WallRoofAdjuster_2
    NEW_ATTRIBUTES = wallOrderID donut
    PYTHONSYMBOL = FeatureProcessor
    PYTHONSOURCE:
      import fme
      import fmeobjects
      import math
      import numpy

      # Finds in which triangle the point p is located
      # Strictly speadking findest the closest corner point
      # since we know that the point is inside one of the triangles.
      # roofTriangle = the roof triangles in self.roofList
      # p = (x,y,z) tuple with the coordinates of the point
      def triangleFinder(roofTriangle,p):
          shortDist = 99999999
          triID = -1 # Which roof triangel the point is inside
          for triKey in roofTriangle:
              tri = roofTriangle[triKey]
              if not triKey == tri.getAttribute('triID'):
                  break # Something wrong with indices
              triGeo = tri.getGeometry()
              triPoly = triGeo.getBoundaryAsCurve()
              triPoints = triPoly.getPoints()

              for tempPoint in triPoints:
                  xyz = tempPoint.getXYZ()
                  tempDist = math.sqrt((xyz[0]-p[0])**2 + (xyz[1]-p[1])**2)
                  if tempDist < shortDist:
                      shortDist = tempDist
                      triID = triKey

          return triID



      # Calculating the offset of the z-coordinate
      # tri = current triangle
      # point = current point
      def zOffset(tri, point):
          # To get (x,y,z) tuples from the triangle
          triGeo = tri.getGeometry()
          triPoly = triGeo.getBoundaryAsCurve()
          triPoints = triPoly.getPoints()
          triPoints = triPoints[:3] # Last point is same as first point

          triXYZ = [x.getXYZ() for x in triPoints]

          b = numpy.array([[point[0]],[point[1]],[1]])
          A = numpy.array([[triXYZ[0][0], triXYZ[1][0], triXYZ[2][0]],[triXYZ[0][1], triXYZ[1][1], triXYZ[2][1]],[1,1,1]])
          coeff = numpy.linalg.solve(A, b)

          alfa = coeff[0]
          beta = coeff[1]
          gamma = coeff[2]

          zPoint = triXYZ[0][2] * alfa + triXYZ[1][2] * beta + triXYZ[2][2] * gamma

          return zPoint


      # Template Class Interface:
      # When using this class, make sure its name is set as the value of
      # the 'Class or Function to Process Features' transformer parameter
      class FeatureProcessor(object):
          def __init__(self):
              self.wall = []              # For the wall incl. coordinates of dormer top
              self.roof = []              # For the 45 degree plane
              self.roofTriangles = {}     # For the roof triangles

          def input(self,feature): # This function is called every time a feature is added

              if feature.getAttribute('isWall'):
                  self.wall.append(feature)
              elif feature.getAttribute('triangle'):
                  self.roofTriangles[feature.getAttribute('triID')] = feature
              else:
                  self.roof.append(feature)

          def close(self):

              # Only  included dormers occupying 30% or more of the width of the wall
              if float(self.wall[0].getAttribute('dormerTopX')) >= 30:

                  # Coordinates of top of dormer
                  dtx = float(self.wall[0].getAttribute('dormerTopX'))
                  dty = float(self.wall[0].getAttribute('dormerTopY'))
                  dtz = float(self.wall[0].getAttribute('dormerTopZ'))

                  # Find in which roof triangle the dormer top is located
                  dormerTriangle = triangleFinder(self.roofTriangles, (dtx, dty, dtz))

                  # Find z of the current position of teh 45 degree plane.
                  currentZ = zOffset(self.roofTriangles[dormerTriangle], (dtx, dty, dtz))

                  # Finding offset to dormer top z
                  zo = dtz - currentZ


                  # Lifting the 45 degree plane to touch the top of the dormer
                  for r in self.roof:
                      geo = r.getGeometry()
                      cu = geo.getBoundaryAsCurve()
                      pl = cu.getPoints()
                      colist = [tp.getXYZ() for tp in pl]
                      newpl = []
                      for pnt in pl:
                          co = pnt.getXYZ()
                          # "Lifting" all points so lower side of plane is touching the top of the facade
                          co = (co[0], co[1], co[2] + zo)
                          newpl.append(co)

                      nl = fmeobjects.FMELine(newpl)
                      np = fmeobjects.FMEPolygon(nl)
                      r.setGeometry(np)

                      self.pyoutput(r)

FME custom transformer IntersectionLineCreatetor

SurfaceFootprintReplacer_Input (input)
    -> SurfaceFootprintReplacer
Note: To find footprint for centre point and extent of area
SurfaceFootprintReplacer
    LIGHT_Y = 0
    LIGHT_Z = 1
    OFFSET_Z = 0
    SHADOW_MODE = Overhead Shadow
    LIGHT_X = 0
    FOOTPRINT -> Dissolver
Dissolver
    DEAGGREGATE_INPUT = Yes
    ACCUM_INPUT_ATTRS = Drop Incoming Attributes
    CONNECT_Z_MODE = Ignore
    NO_OVRLP = No
    AREA -> AreaCalculator
Note: Assuming that the largest area is the main footprint
AreaCalculator
    AREA_TYPE = Plane Area
    AREA_ATTR = _area
    MULT = 1
    -> Sorter
Sorter
    SORT_PARM = _area NUMERIC DESCENDING
    SORTED -> Counter
Counter
    START = 0
    SCOPE = Global
    CNT_ATTR = _count
    DOMAIN = counter
    -> Tester
Tester
    TEST_MODE = Automatic
    TEST_CLAUSE = TEST @Value(_count) = 0
    BOOL_OP = OR
    PASSED -> CoordinateExtractor
Note: To find max x value of the footprint
CoordinateExtractor
    LIST_NAME = _indices
    MODE = All Coordinates
    -> ListRangeExtractor
ListRangeExtractor
    SRC_LIST = _indices{}.x
    MIN = minX
    MAX = maxX
    -> AttributeRemover
Note: Removing list of coordinates
Note: Here a centre point inside the footprint is found and a line starting / from the centre point is used to find / one outer wall via intersection
AttributeRemover
    LIST_ATTRS = _indices{} _indices{}.x _indices{}.y _indices{}.z
    -> CenterPointReplacer
Note: To get only one line. / NB! what is best centre point? / Now "inside" is selected to force it to be inside the footprint
CenterPointReplacer
    MODE = Inside Point
    POINT -> CoordinateExtractor_2
CoordinateExtractor_2
    LIST_NAME = _indices
    MODE = All Coordinates
    -> Extruder
Extruder
    EXTRUSION_Y = 0.0
    EXTRUSION_Z = 0.0
    DIRECTION = Specified
    EXTRUSION_X = @Value(maxX) - @Value(minX)
    EXTRUDED -> AttributeCreator
Note: To identify line after intersection
AttributeCreator
    ATTR_TABLE = SET_TO IntersectLine = line
    -> AttributeKeeper
AttributeKeeper
    KEEP_ATTRS = IntersectLine
    -> 2DForcer_2
2DForcer_2
    2D -> 2DForcer_2_2D (output)
2DForcer_2_2D (output)

FME custom transformer IFC2CityGML_Geometryconverter_parts

GeometryPartExtractor_2_Input (input)
    -> GeometryPartExtractor_2
Note: Check that geometry name is solid
GeometryPartExtractor_2
    EXTRACTTYPE_PARAM = Extract
    GQUERY:
      for $geom in //geometry
      where $geom/@fme_geometry_name = 'Body'
      return number($geom/@fme_id)
    PROCESSED -> GeometryCoercer_2
    UNTOUCHED -> GeometryCoercer_2
Note: Check for geometry type IFMEExtrusion OR IFMEBRepSolid
GeometryCoercer_2
    KIND = fme_composite_surface
    GQUERY:
      for $geom in //geometry
      where $geom/@fme_geometry_type = 'IFMEExtrusion'
      or $geom/@fme_geometry_type = 'IFMEBRepSolid'
      return number($geom/@fme_id)
    COERCED -> Deaggregator
    UNTOUCHED -> Deaggregator
Note: Changed split compostites to YES
Deaggregator
    SPLIT_COMPOSITES = Yes
    GEOM_NAME_FIELD = _geometry_name
    LIST_ATTR_MODE_LOOKUP = LEAN
    MODE = Flatten All Levels
    EXPLODE_INSTANCES = No
    DEAGGREGATED -> GeometryRefiner
Note: Keep this or not?
GeometryRefiner
    -> Output (output)
Output (output)

FME custom transformer NormalVectorFinder

CoordinateExtractor_Input (input)
    -> CoordinateCounter
Note: Note that there are wall surfaces (beloning to "Takplan" in KTH where index 0 is in a vertical line with both first and second last index ont eh line i.e. the normals arr not correct.
NormVec_Output (output)

Bookmark: Calculate Normal Vector (_vx, _vy, _vz)
  There was a special case with one outer wall surface (see notes) which gave wrong orientation due to concave shape. This version is using coordinates with index 0, 1, (nbr coords -4) to test if that solves the problem. See notes for more details.
Note: Need to know the number of / coordinates to find the second / last.
CoordinateCounter
    CNT_ATTR = _coordcount_normal_vector
    -> CoordinateExtractor_7
CoordinateExtractor_7
    Z_DEFAULT = -9999
    IND = 0
    X_ATTR = _x0
    Y_ATTR = _y0
    Z_ATTR = _z0
    -> CoordinateExtractor_8
Note: Should be index 1 and that works fine with FME2017 but for some reason 1 is not a valid index with FME2018.1. Index 2 seems to work fine though......
CoordinateExtractor_8
    Z_DEFAULT = -9999
    IND = 1
    X_ATTR = _x1
    Y_ATTR = _y1
    Z_ATTR = _z1
    -> CoordinateExtractor_9
CoordinateExtractor_9
    Z_DEFAULT = -9999
    IND = @Value(_coordcount_normal_vector)-2
    X_ATTR = _x2
    Y_ATTR = _y2
    Z_ATTR = _z2
    -> AttributeCreator_5
AttributeCreator_5
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_6
AttributeCreator_6
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))
    -> AttributeRemover
AttributeRemover
    REMOVE_ATTRS = _coordcount_normal_vector
    -> NormVec_Output (output)

Bookmark: Calculate Normal Vector (_vx, _vy, _vz)
CoordinateExtractor
    Z_DEFAULT = -9999
    IND = 0
    X_ATTR = _x0
    Y_ATTR = _y0
    Z_ATTR = _z0
    -> CoordinateExtractor_2
CoordinateExtractor_2
    Z_DEFAULT = -9999
    IND = 1
    X_ATTR = _x1
    Y_ATTR = _y1
    Z_ATTR = _z1
    -> CoordinateExtractor_3
CoordinateExtractor_3
    Z_DEFAULT = -9999
    IND = 3
    X_ATTR = _x2
    Y_ATTR = _y2
    Z_ATTR = _z2
    -> AttributeCreator
AttributeCreator
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_2
AttributeCreator_2
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))
