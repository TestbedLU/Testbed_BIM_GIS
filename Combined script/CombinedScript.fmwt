FME workspace CombinedScript.fmwt
Title: CombinedScript

Parameters:
- SourceDataset_IFC = $(FME_MF_DIR)2/wb_template_1530871619264_7736/180430 - House 45.ifc   # Source Industry Foundation Class (IFC) File(s)
- SourceDataset_XML = $(FME_MF_DIR)2/wb_template_1530871619264_7736/ArildCentral.xml   # Source XML File(s)
- SourceDataset_GML = $(FME_MF_DIR)2/wb_template_1530871619264_7736/ArildCentral.xml   # Source Geography Markup Language (GML) File(s)
- SourceDataset_GEOTIFF = $(FME_MF_DIR)1/Skript från Per-Ola/DEM_Arild_2.tif   # Source GeoTIFF File(s)
- DEM_resolution = 2   # DEM resolution
- zOffset2 = 20   # " " Attribute Value
- uttagDatum = 20180702100300   # Välj datum för uttag av datamängd ur lager
- DestDataset_TEXTLINE_3 = C:\Users\JOSEFI~1\AppData\Local\Temp\wb_template_1530695523598_7632\BY_Byggnad_v3.0_KTH_solid.xml   # Destination Text File
- dimension = 3   # Välj dimension
- koordinatsystemPlan = EPSG:3008   # Välj koordinatsystem i plan
- koordinatsystemPlanIdentifier = urn:ogc:def:crs:EPSG::3008   # Välj identifier för koordinatsystem i plan
- byggnadNamn = KTH demo   # " " byggnadNamn
- byggnadAndamal = verksamhet   # " " byggnadAndamal
- status = planerad   # " " status
- byggnadNummer = 201   # " " byggnadNummer
- bygglovAtgardTyp = nybyggnad   # " " bygglovAtgardTyp
- bygglovStatusTyp = slutbesked   # " " bygglovStatusTyp
- atgardAr_bygglovstatus = 2016-05-01T14:07:00+00:00   # " " atgardAr_bygglovstatus
- beslutsdatum_bygglovStatus = 2016-05-01T14:07:00+00:00   # " " beslutsdatum_bygglovStatus
- decimalPlaces = 2   # Decimal Places
- ofriGrund = false   # " " ofriGrund
- id_datamangd_versionId = 1   # " " id_datamangd_versionId
- id_byggnad_versionId = 1   # " " id_byggnad_versionId
- coClassID = 1HeRFbeBDBIuMgfcpC1nk_   # " " coClassID
- coClassKod = BV   # " " coClassKod
- planlagetyp = fasad   # " " planlagetyp

Readers:
- IFC_1: IFC from $(SourceDataset_IFC)
- XML_1: XML from $(SourceDataset_XML)
- GML_1: GML from $(SourceDataset_GML)
- GEOTIFF_1: GEOTIFF from $(SourceDataset_GEOTIFF)

Writers:
- TEXTLINE_1: TEXTLINE to $(DestDataset_TEXTLINE_3)

Note: Combined script / This workspace is released under the 3-Clause BSD License. For details, see the Description of this workspace. See also https://opensource.org/licenses/BSD-3-Clause / This script contains: / Detailed development plan reader / IFC reader / Building footprint area calculation / Building height calculation / Compliance checking between calculated values and the detailed development plan / Conversion between IFC and SGP (Svensk geoprocess) 3.0 / DEM reader
IfcSlab_-__SGPGeometry_LOD2_StoreyIndexFinder_AttributeCreator_StoreyList_Input_1: Junction
    -> CoordinateExtractor
    -> StoreyIndexFinder [AttributeCreator_StoreyList_Input]
IfcWallStandardCase_-__FootprintAreaCalculator_All_ListBasedFeatureMerger: Junction
    -> FootprintAreaCalculator [All_ListBasedFeatureMerger]
    -> FootprintAreaCalculator [Clipper_Max_3m_Input]
    -> FootprintAreaCalculator [Clipper_Max_5m_Input]

Bookmark: XML Reader
plus (reader XML_1)
    attributes: plus xml_char(1), plus.href xml_char(6), xml_fragment xml_xml, xml_id xml_char(19), xml_matched_element xml_char(5), xml_parent_child_pos xml_decimal(3,0), xml_parent_id xml_char(21)
    -> detaljPlanReader [Aggregator_Input]
minus (reader XML_1)
    attributes: minus xml_char(1), minus.href xml_char(6), xml_fragment xml_xml, xml_id xml_char(20), xml_matched_element xml_char(6), xml_parent_child_pos xml_decimal(3,0), xml_parent_id xml_char(21)
    -> detaljPlanReader [Aggregator_Input]
DP_Omrade (reader XML_1)
    attributes: DP_Omrade.id xml_char(3), minus xml_char(1), minus.href xml_char(6), minus{} xml_char(1), minus{}.href xml_char(6), plus xml_char(1), plus.href xml_char(6), plus{} xml_char(1), plus{}.href xml_char(6), xml_fragment xml_xml, xml_id xml_char(21), xml_matched_element xml_char(10), xml_parent_child_pos xml_char(1), xml_parent_id xml_char(1)
    -> detaljPlanReader [FeatureMerger_Supplier]

Bookmark: GML Reader
DP_Grans (reader GML_1)
    attributes: typ{} xml_char(5), linje xml_geometry
    -> detaljPlanReader [AttributeCreator_2_Input]
DP_Omrade (reader GML_1)
    attributes: plus.nilReason xml_buffer, plus.gml_remoteSchema xml_buffer, plus.xlink_href xml_buffer, plus.xlink_title xml_buffer, plus.owns xml_boolean, minus.nilReason xml_buffer, minus.gml_remoteSchema xml_buffer, minus.xlink_href xml_buffer, minus.xlink_title xml_buffer, minus.owns xml_boolean
    -> detaljPlanReader [FeatureMerger_Requestor]
DP_Egenskapsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> detaljPlanReader [PythonCaller_Byggnadshojd_Input]
DP_Anvandningsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, anvandningsslag xml_buffer, precisering xml_buffer, huvudsaklig xml_boolean, egenskapsbestammelse{}.nilReason xml_buffer, egenskapsbestammelse{}.gml_remoteSchema xml_buffer, egenskapsbestammelse{}.xlink_href xml_buffer, egenskapsbestammelse{}.xlink_title xml_buffer, egenskapsbestammelse{}.owns xml_boolean, administrativBestammelse{}.nilReason xml_buffer, administrativBestammelse{}.gml_remoteSchema xml_buffer, administrativBestammelse{}.xlink_href xml_buffer, administrativBestammelse{}.xlink_title xml_buffer, administrativBestammelse{}.owns xml_boolean
    -> detaljPlanReader [FeatureMerger_Anvandning_Supplier]

Bookmark: Detailed development plan
  Read and modify the detailed development plan
Note: Detaljplan / Detailed development plan / Källa: Höganäs kommun, Stadsbyggnadskontoret / Source: Höganäs municipality, Urban planning office
detaljPlanReader
    MINUS.HREF = @Value(minus.href)
    OMRADE.XLINK_HREF = @Value(omrade.xlink_href)
    BETECKNING = @Value(beteckning)
    BESTAMMELSETYP = @Value(bestammelsetyp)
    GML_ID = @Value(gml_id)
    XML_ID = @Value(xml_id)
    UUID = @Value(uuid)
    URSPRUNGLIG = @Value(ursprunglig)
    ANVANDNINGSSLAG = @Value(anvandningsslag)
    XML_PARENT_CHILD_POS = @Value(xml_parent_child_pos)
    PLUS.HREF = @Value(plus.href)
    DP_OMRADE.ID = @Value(DP_Omrade.id)
    XML_PARENT_ID = @Value(xml_parent_id)
    TestFilter_2_prickMark -> FeatureColorSetter_prickadMark
    TestFilter_2_korsMark -> FeatureColorSetter_korsMark
    TestFilter_Gata -> detaljPlanReader_TestFilter_Cykel_-__detaljPlanReader_TestFilter_Cykel
    TestFilter_Gång -> detaljPlanReader_TestFilter_Cykel_-__detaljPlanReader_TestFilter_Cykel
    TestFilter_Cykel -> detaljPlanReader_TestFilter_Cykel_-__detaljPlanReader_TestFilter_Cykel
    TestFilter_Vatten -> FeatureColorSetter_Vatten
    TestFilter__Unfiltered_ -> FeatureColorSetter_OtherAreas
Junction_14
    -> Junction_15
Junction_16
    -> Junction_17
detaljPlanReader_TestFilter_Cykel_-__detaljPlanReader_TestFilter_Cykel: Junction
    -> FeatureColorSetter_Gata_gang
    -> detaljPlanReader_TestFilter_Cykel_-__detaljPlanReader_TestFilter_Cykel_Output_-__Clipper_CLIPPER
Junction_18
    -> Junction_19
Note: mainWallFinder : Input
Junction_9
    -> Junction_10
detaljPlanReader_TestFilter_Cykel_-__detaljPlanReader_TestFilter_Cykel_Output_-__Clipper_CLIPPER: Junction
    -> Clipper [CLIPPER]
    -> Junction_5
Junction_20
    -> Junction_21
Junction_22
    -> Junction_23
Note: Removing the area / covering the entire / plan
Tester_EntirePlan
    TEST_DESCRIPTION = ""
    TEST_CLAUSE = TEST @Value(ID_join) != #a
    BOOL_OP = OR
    TEST_MODE = Automatic
    PASSED -> Clipper [CLIPPEE]
    PASSED -> Junction_5
    PASSED -> Tester_EntirePlan_Passed
    PASSED -> Junction_4
Tester_EntirePlan_Passed: Inspector
Note: BuildingHeightCheckerNe_DevelopmentPlan_Input : Input
Junction_5
    -> Junction_6
Note: AreaComplianceCheck : Clipper_2_Clippee
Junction_4
    -> Junction_11

Bookmark: Set area color for visualization
FeatureColorSetter_prickadMark
    COLOR = 0,0,0
    MODE = Fixed
    FILL_COLOR = 1,0.14902,0.160784
    COLORED -> FeatureColorSetter_prickadMark_COLORED_-__Junction_10
    COLORED -> detaljPlanReader_TestFilter_Cykel_-__detaljPlanReader_TestFilter_Cykel_Output_-__Clipper_CLIPPER
    COLORED -> Junction_14
FeatureColorSetter_korsMark
    COLOR = 0,0,0
    MODE = Fixed
    FILL_COLOR = 0.423529,0.0627451,0.0666667
    COLORED -> FeatureColorSetter_prickadMark_COLORED_-__Junction_10
    COLORED -> detaljPlanReader_TestFilter_Cykel_-__detaljPlanReader_TestFilter_Cykel_Output_-__Clipper_CLIPPER
    COLORED -> Junction_16
FeatureColorSetter_Gata_gang
    COLOR = 0.666667,0.556863,0.552941
    MODE = Fixed
    FILL_COLOR = 0.666667,0.556863,0.552941
    COLORED -> FeatureColorSetter_prickadMark_COLORED_-__Junction_10
    COLORED -> Junction_9
    COLORED -> Junction_18
FeatureColorSetter_Vatten
    COLOR = 0,0,1
    MODE = Fixed
    FILL_COLOR = 0,0,1
    COLORED -> Junction_20
FeatureColorSetter_OtherAreas
    COLOR = 0,0,0
    MODE = Fixed
    FILL_COLOR = 0.666667,1,0.498039
    COLORED -> Tester_EntirePlan
    COLORED -> Junction_22

Bookmark: Inspectors
Note: FeatureColorSetter_prickadMark : Colored
Junction_15
    -> FeatureColorSetter_prickadMark_Colored
FeatureColorSetter_prickadMark_Colored: Inspector
Note: FeatureColorSetter_korsMark : Colored
Junction_17
    -> FeatureColorSetter_korsMark_Colored
FeatureColorSetter_korsMark_Colored: Inspector
Note: FeatureColorSetter_Gata_gang : Colored
Junction_19
    -> FeatureColorSetter_Gata_gang_Colored
FeatureColorSetter_Gata_gang_Colored: Inspector
Note: FeatureColorSetter_Vatten : Colored
Junction_21
    -> FeatureColorSetter_Vatten_Colored
FeatureColorSetter_Vatten_Colored: Inspector
Note: FeatureColorSetter_OtherAreas : Colored
Junction_23
    -> FeatureColorSetter_OtherAreas_Colored
FeatureColorSetter_OtherAreas_Colored: Inspector
DetailedPlan_draped: Inspector

Bookmark: Draping detailed development plan on DEM for visualization
FeatureColorSetter_prickadMark_COLORED_-__Junction_10: Junction
    -> SurfaceDraper [DRAPE_FEATURES]
Note: TINGenerator_DEM : Triangles
Junction_3
    -> SurfaceDraper [POINTS/LINES]
SurfaceDraper
    TOLERANCE = 1
    ADDZ_TYPE = Replace Z
    DRAPE_TYPE = VERTEX
    INTERPOLATION_TYPE = AUTO
    DRAPED_FEATURES -> DetailedPlan_draped

Bookmark: "Transforming" the building
  "Transforming" (=translate and rotate) the building. The building is a surface model that is transformed from IFC-model to GIS (surface model).
Note: FeatureColorSetter_Gata_gang : Colored
Junction_10
    -> mainWallFinder [Intersector_Input]
AttributeCreator_Offset
    ATTR_TABLE = SET_TO zOffset = $(zOffset2)
    -> Offsetter_2
Offsetter_2
    ZOFF = @Value(zOffset)
    MODE = Cartesian Coordinate
    YOFF = 6239396
    XOFF = 92770
    OFFSET -> Rotator
Rotator
    ANGLE = 156
    YORIG = 6239396
    XORIG = 92770
    ROTATED -> importedBuilding
    ROTATED -> TestFilter
importedBuilding: Inspector
TestFilter
    DEFAULT_VALUE = <UNFILTERED>
    TEST_LIST = BOOL_OP,OR,COMPOSITE_TEST,<Unused>,TEST_CLAUSE,"TEST @Value(type) = mainWalls",mainWalls
    mainWalls -> 2DForcer_buildingImport
    mainWalls -> mainWallFinder [inputWalls]
2DForcer_buildingImport
    2D -> 2DForcer_buildingImport_2D_-__BuildingHeightCheckerNew_2DForcer_buildingImport
Note: Find the main wall according to current regualtions, / i.e. the wall with teh greatest visual impact to / the public. Identified as the wall closets to public / street(car, bike, pedestrian)
mainWallFinder
    WALLORDERID = @Value(wallOrderID)
    WALLHEIGHTNEW = @Value(wallHeightNEW)
    WALLHEIGHTOLD = @Value(wallHeightOLD)
    mainWallFinder_Output -> mainWallFinder_mainWallFinder_Output_-__BuildingHeightCheckerCurrent_mainWallFinder

Bookmark: Clipping overlapping areas for visualtisation.
  The area covering the entire plan is clipped where it overlaps other areas. Purely for visualisation.
Clipper
    BOUNDARY_CASES = Treat as Inside
    LINES_AS_SEGMENTS = No
    CLIPPED_ATTR = _clipped
    ATTR_CONFLICT_RES = Use Clippee
    MISSING_VAL_MODE = Compute
    MEASURE_TYPE = Continuous
    CLIP_TYPE = Multiple Clippers
    PRESERVE_CLIPPEE_EXTENTS = No
    DEFAULT_VAL = 0
    VAL_SOURCE = Clippee Only
    CREATE_AGGREGATES = Yes
    CONNECT_Z_MODE = First Wins
    ATTR_ACCUM_MODE = Merge Clipper
    OUTSIDE -> SurfaceDraper [DRAPE_FEATURES]

Bookmark: Building height calculation
Junction_6
    -> BuildingHeightCheckerNew [DevelopmentPlan_Input]
    -> BuildingHeightCheckerCurrent [DevelopmentPlan_Input]
Note: RasterCellCoercer_DEM : Output
Junction_8
    -> RasterCellCoercer_DEM_OUTPUT_-__BuildingHeightCheckerNew_from_DEM_2
RasterCellCoercer_DEM_OUTPUT_-__BuildingHeightCheckerNew_from_DEM_2: Junction
    -> BuildingHeightCheckerNew [from_DEM_2]
    -> BuildingHeightCheckerNew [from_DEM]
    -> BuildingHeightCheckerCurrent [from_DEM_2]
    -> BuildingHeightCheckerCurrent [from_DEM]
Note: Checking building height according to the "new" method, / i.e. the highest facade of the building is used to derive / building height regardless of orientation. / NB!!! / Connect 2DForcer_buildingImport to both: / 2DForcer_buildingImport and / 2DForcer_buildingImport_2 / Connect RasterCellCoercer_DEM to both: / from_DEM_2 and / from_DEM
BuildingHeightCheckerNew
    maxHeight_if_too_high -> BuildingHeightCheckerNew_maxHeight_if_too_high
    groundElevation -> BuildingHeightCheckerNew_groundElevation
BuildingHeightCheckerNew_maxHeight_if_too_high: Inspector
BuildingHeightCheckerNew_groundElevation: Inspector
Note: Checking building height according to the "new" method, / i.e. the highest facade of the building is used to derive / building height regardless of orientation. / NB!!! / mainWallFinder to both: / 2DForcer_buildingImport and / 2DForcer_buildingImport_2 / Connect RasterCellCoercer_DEM to both: / from_DEM_2 and / from_DEM
BuildingHeightCheckerCurrent
    maxHeight_if_too_high -> BuildingHeightCheckerCurrent_maxHeight_if_too_high
    groundElevation -> BuildingHeightCheckerCurrent_groundElevation
Note: Plane showing max height if building too high.
BuildingHeightCheckerCurrent_maxHeight_if_too_high: Inspector
Note: Plane showing mean ground elevation.
BuildingHeightCheckerCurrent_groundElevation: Inspector

Bookmark: Building model
Note: Tester_EntirePlan : Passed
Junction_11
    -> AreaComplianceCheck [Clipper_2_Clippee]
2DForcer_buildingImport_2D_-__BuildingHeightCheckerNew_2DForcer_buildingImport: Junction
    -> BuildingHeightCheckerNew [2DForcer_buildingImport]
    -> BuildingHeightCheckerNew [2DForcer_buildingImport_2]
Note: detaljPlanReader and / Clipper_CLIPPER : Output
mainWallFinder_mainWallFinder_Output_-__BuildingHeightCheckerCurrent_mainWallFinder: Junction
    -> BuildingHeightCheckerCurrent [mainWallFinder]
    -> BuildingHeightCheckerCurrent [mainWallFinder_2]

Bookmark: DEM - digital elevation model
  Importing and preparing DEM. The DEM is used to find the mean ground elevation where the building is placed.
GEOTIFF (reader GEOTIFF_1)
    -> RasterCellCoercer_DEM
Note: To find building height.
RasterCellCoercer_DEM
    PRESERVE_ATTRIBUTES = No
    EXTRACT_NODATA = No
    CELL_GEOMETRY = Points
    EXTRACT_BAND_VALUES_AS = Z Values
    -> TINGenerator_DEM [POINTS/LINES]
    -> Junction_7
Note: BuildingHeightCheckerNew_ / from_DEM_2 : Input
Junction_7
    -> Junction_8
Note: For draping planning map.
TINGenerator_DEM
    TOLERANCE = 0.01
    TRIANGLES -> Junction
Note: Junction_5 : Input
Junction
    -> Junction_3

Bookmark: IFC Reader
IfcSlab (reader IFC_1)
    attributes: GlobalId char(22), Name string, Description string, ObjectType string, Tag string, PredefinedType enumeration, Axis geometry, Body geometry, Box geometry, FootPrint geometry
    -> IfcWallStandardCase_-__FootprintAreaCalculator_All_ListBasedFeatureMerger
    -> IfcSlab_-__SGPGeometry_LOD2_StoreyIndexFinder_AttributeCreator_StoreyList_Input_1
    -> Junction_12
Note: Ifc2surfacesParts : Input
Junction_12
    -> Junction_13
IfcRoof (reader IFC_1)
    attributes: GlobalId char(22), Name string, Description string, ObjectType string, Tag string, ShapeType enumeration, Axis geometry, Body geometry, Box geometry, FootPrint geometry
    -> IfcWallStandardCase_-__FootprintAreaCalculator_All_ListBasedFeatureMerger
    -> IFC2CityGML_Geometryconverter_parts_Roof [GeometryPartExtractor_2_Input]
    -> FootprintAreaCalculator [IfSlab_Input]
IfcBuildingStorey (reader IFC_1)
    attributes: GlobalId char(22), Name string, Description string, ObjectType string, LongName string, CompositionType enumeration, Elevation real, Axis geometry, Body geometry, Box geometry, FootPrint geometry
    -> StoreyIndexFinder [PythonCaller_2_Input]
    -> FootprintAreaCalculator [BuildingStorey_AggregatedList]
IfcWallStandardCase (reader IFC_1)
    attributes: GlobalId char(22), Name string, Description string, ObjectType string, Tag string, Axis geometry, Body geometry, Box geometry, FootPrint geometry
    -> IfcWallStandardCase_-__FootprintAreaCalculator_All_ListBasedFeatureMerger
    -> IFC2CityGML_Geometryconverter_parts_Walls [GeometryPartExtractor_2_Input]
    -> FootprintAreaCalculator [Clipper_BottomEdge_Input]
IfcWindow (reader IFC_1)
    attributes: GlobalId char(22), Name string, Description string, ObjectType string, Tag string, OverallHeight real, OverallWidth real, Axis geometry, Body geometry, Box geometry, FootPrint geometry
    -> IFC2CityGML_Geometryconverter_parts_Window [GeometryPartExtractor_2_Input]
IfcDoor (reader IFC_1)
    attributes: GlobalId char(22), Name string, Description string, ObjectType string, Tag string, OverallHeight real, OverallWidth real, Axis geometry, Body geometry, Box geometry, FootPrint geometry
    -> IFC2CityGML_Geometryconverter_parts_Door [GeometryPartExtractor_2_Input]

Bookmark: Finding max and min Z-ccord of the building
  Used to get relative height (highest point of roof and lowest part of building) 
  and to extrude the footprint to a 3D solid.
CoordinateExtractor
    MODE = All Coordinates
    LIST_NAME = _indices
    -> ListRangeExtractor
ListRangeExtractor
    MAX = _maxZ
    MIN = _minZ
    SRC_LIST = _indices{}.z
    -> Aggregator
Aggregator
    ORDERED = No
    MODE = Geometry - Assemble One Level
    ACCUM_ATTRS_NAME = Merge Incoming Attributes
    SEP = ,
    AGGREGATE_TYPE = Homogeneous Collection (If Possible)
    LIST_ATTRS_TO_INCLUDE = _maxZ _minZ
    LIST_NAME = _minMaxZList
    AGGREGATE -> ListRangeExtractor_2
ListRangeExtractor_2
    MAX = _maxZBuilding
    MIN = _junk
    SRC_LIST = _minMaxZList{}._maxZ
    -> ListRangeExtractor_3
ListRangeExtractor_3
    MAX = _junk
    MIN = _minZBuilding
    SRC_LIST = _minMaxZList{}._minZ
    -> AttributeKeeper
AttributeKeeper
    KEEP_ATTRS = _maxZBuilding,_minZBuilding
    -> PythonCaller_Z_limit_adder

Bookmark: Create Surface model
Note: IfcSlab
Junction_13
    -> Ifc2surfacesParts [IntersectionLineCreatetor_SurfaceFootprintReplacer_Input_1]
IFC2CityGML_Geometryconverter_parts_Roof
    -> NormalVectorFinder_2 [CoordinateExtractor_Input]
NormalVectorFinder_2
    NormVec_Output -> Ifc2surfacesParts [NormalVectorFinder_Roof_CoordinateExtractor_Input]
IFC2CityGML_Geometryconverter_parts_Walls
    -> NormalVectorFinder_3 [CoordinateExtractor_Input]
NormalVectorFinder_3
    NormVec_Output -> Ifc2surfacesParts [NormalVectorFinder_Walls_CoordinateExtractor_Input]
IFC2CityGML_Geometryconverter_parts_Window
    -> NormalVectorFinder [CoordinateExtractor_Input]
NormalVectorFinder
    NormVec_Output -> Ifc2surfacesParts [NormalVectorFinder_2_CoordinateExtractor_Input]
IFC2CityGML_Geometryconverter_parts_Door
    -> Ifc2surfacesParts [BinaryEncoder_Door_Input]
Ifc2surfacesParts
    IFC_UNIQUE_ID = @Value(ifc_unique_id)
    GML_PARENT_ID = @Value(ifc_parent_unique_id)
    _VZ = @Value(_vz)
    IFC_PARENT_UNIQUE_ID = @Value(ifc_parent_unique_id)
    AttributeKeeper_6_Output -> AttributeCreator_Offset

Bookmark: IFC 2 SGP LOD2
Note: Copyright (c) 2018, Lantmäteriet / All rights reserved. / This workspace is released under the 3-Clause BSD License. For details, see the Description of this workspace. See also https://opensource.org/licenses/BSD-3-Clause
Note: Obs! Publika parametrar (från LMs original): / uttagDatum: Obligatorisk; värde väljs manuellt / namnDatamängd: Obligatorisk; värde väljs manuellt / dimension: Obligatorisk; värde väljs manuellt / koordinatsystemPlan: Obligatorisk; värde väljs manuellt / koordinatsystemPlanIdentifier: Obligatorisk; värde väljs manuellt
StoreyIndexFinder
    storeyIndex = 0
    IFC_UNIQUE_ID = @Value(ifc_unique_id)
    Tester_StoreyIndex_Passed -> SurfaceFootprintReplacer
Note: Adding attributes for max and / min Z to the footprint for later / extrusion.
PythonCaller_Z_limit_adder
    PYTHONSYMBOL = FeatureProcessor
    PYTHONSOURCE:
      import fme
      import fmeobjects
      import numpy

      # Template Class Interface:
      # When using this class, make sure its name is set as the value of
      # the 'Class or Function to Process Features' transformer parameter
      class FeatureProcessor(object):
          def __init__(self):
              self.featureList = []
              self.maxZ = None
              self.minZ = None

          def input(self,feature):
              if feature.getAttribute('_maxZBuilding'):
                  self.maxZ = float(feature.getAttribute('_maxZBuilding'))
                  self.minZ = float(feature.getAttribute('_minZBuilding'))
              else:
                  self.featureList.append(feature)

          def close(self):
              for f in self.featureList:
                  f.setAttribute('maxZBuilding', self.maxZ)
                  f.setAttribute('minZBuilding', self.minZ)
                  f.setAttribute('diffZBuilding', self.maxZ - self.minZ)

                  self.pyoutput(f)
    NEW_ATTRIBUTES = maxZBuilding minZBuilding diffZBuilding
    -> PythonCaller_Z_limit_adder_2
Note: Adding attribute for building area / and attribute to state that area exists.
PythonCaller_Z_limit_adder_2
    PYTHONSYMBOL = FeatureProcessor
    PYTHONSOURCE:
      import fme
      import fmeobjects
      import numpy

      # Template Class Interface:
      # When using this class, make sure its name is set as the value of
      # the 'Class or Function to Process Features' transformer parameter
      class FeatureProcessor(object):
          def __init__(self):
              self.featureList = []
              self.byArea = None

          def input(self,feature):
              if feature.getAttribute('_area'):
                  self.byArea = int(round(float(feature.getAttribute('_area'))))
              else:
                  self.featureList.append(feature)

          def close(self):
              for f in self.featureList:
                  f.setAttribute('byggnadsArea', self.byArea)
                  f.setAttribute('byAreaExists', 1)

                  self.pyoutput(f)
    NEW_ATTRIBUTES = byggnadsArea byAreaExists
    -> Rotator_3
UUIDGenerator_BDM
    UUID_ATTR = _uuid_BDM
    -> BY_BDM
Note: Ändrar datum-formatet / för attributet till ISO- / format.
DateTimeConverter
    REPAIR_INPUT = NO
    OUT_FORMAT = ISO
    DATETIME_ATTR = _BDM_uttagDatum
    -> StringConcatenator_8
Note: "Transformation" / The IFC models is "transformed" to SWEREF99 13 30 by rough rotation - scaling - translation.
AttributeKeeper_2
    KEEP_ATTRS = diffZBuilding,_maxZBuilding,maxZBuilding,byAreaExists,byggnadsArea
    -> AttributeCreator_RelativHojd
AttributeCreator_RelativHojd
    ATTR_TABLE:
      SET_TO relHojd = @Evaluate(@Value(diffZBuilding)*0.001)
      SET_TO hogstaHojd = takets högsta punkt (nock)
      SET_TO lagstaHojd = byggnadens lägsta punkt
    -> AttributeCreator
AttributeCreator
    ATTR_TABLE = SET_TO planLageTyp = $(planlagetyp)
    -> AttributeRounder_2
AttributeRounder_2
    SRC_ATTRS = relHojd
    ROUND_TYPE = Nearest
    PLACES = 2
    -> UUIDGenerator_BD
Note: UUID for ByggadsDel
UUIDGenerator_BD
    UUID_ATTR = _uuid_BYD
    -> Extruder
    -> PythonCaller_WallCreator_2
    -> Offsetter_wallSurface
Note: To create 3D model
Note: Round to two decimals
Extruder
    DISTANCE = @Value(relHojd)
    DIRECTION = Vertical
    EXTRUDED -> CoordinateSystemSetter
    EXTRUDED -> BoundsExtractor_2
Note: Note that the attribute for geometry must be / changed depending on geometry type: / _BD_lod2_kropp = _geometri_BYD_solid / _BD_lod2_ytgeometri = _geometri_BYD_surface
UUIDGenerator_B
    UUID_ATTR = _uuid_B
    -> BY_B
BY_B_Output: Inspector
CoordinateSystemSetter
    COORDSYS = $(koordinatsystemPlan)
    -> CoordinateRounder_2
CoordinateRounder_2
    YPREC = $(decimalPlaces)
    ZPREC = $(decimalPlaces)
    XPREC = $(decimalPlaces)
    ROUNDED -> GeometryExtractor_2
Note: To get "fake" serial ID for / different building parts.
Counter
    SCOPE = Local
    CNT_ATTR = _count_bd
    DOMAIN = counter
    START = 101
    -> StringConcatenator_12
CoordinateSystemSetter_2
    COORDSYS = $(koordinatsystemPlan)
    -> CoordinateRounder
CoordinateRounder
    YPREC = $(decimalPlaces)
    ZPREC = $(decimalPlaces)
    XPREC = $(decimalPlaces)
    ROUNDED -> GeometryExtractor_3
GeometryExtractor_3
    PREFER_POLYGON_OVER_SURFACE = No
    OMIT_NAMESPACES_DISPLAY = No
    ATTR = _geometri_surface
    OGEOSMS_URL_PREFIX = http://maps.google.com/?q=
    KIND_LONG = GML v3.2.1
    OGCVERSION = 1.2
    REMOVE_GEOMETRY = No
    OGC_WKT_PRECISION_DISPLAY = Shortened 64-bit
    -> StringReplacer_9
StringReplacer_9
    SRC_ATTRS = _geometri_surface
    NO_MATCH = _FME_NO_OP_
    FIND_TEXT = $(koordinatsystemPlan)
    CASE = NO
    REGEXP = NO
    REPLACE_TEXT = $(koordinatsystemPlanIdentifier)
    -> UUIDGenerator_BY
UUIDGenerator_BY
    UUID_ATTR = _uuid_BY
    -> BY_BY
TestFilter_2
    DEFAULT_VALUE = <UNFILTERED>
    TEST_LIST = BOOL_OP,OR,COMPOSITE_TEST,<Unused>,TEST_CLAUSE,"TEST @Value(surfaceType) = roof",Tak,BOOL_OP,OR,COMPOSITE_TEST,<Unused>,TEST_CLAUSE,"TEST @Value(surfaceType) = wall",Vägg,BOOL_OP,OR,COMPOSITE_TEST,<Unused>,TEST_CLAUSE,"TEST @Value(surfaceType) = bottom",Botten
    Tak -> StringConcatenator_11
    Vägg -> StringConcatenator_10

Bookmark: Creating simplified footprint
  Replaces the slab with it's footprint and dissolves to get oen polygon.
  Generalizing to remove small balconies etc. 
  The start and end of the permeter was in a dent of the outer wall and could not be removed by generaliazaion. To solve this a hard coded python script was added.
SurfaceFootprintReplacer
    LIGHT_X = 0
    OFFSET_Z = 0
    LIGHT_Y = 0
    LIGHT_Z = 1
    SHADOW_MODE = Overhead Shadow
    FOOTPRINT -> Dissolver_2
    <REJECTED> -> SurfaceFootprintReplacer__Rejected_
Dissolver_2
    ACCUM_INPUT_ATTRS = Use Attributes From One Feature
    NO_OVRLP = No
    CONNECT_Z_MODE = First Wins
    DEAGGREGATE_INPUT = Yes
    AREA -> PythonCaller_Coordinate_remover
    <REJECTED> -> Dissolver__Rejected_
Note: Change range in PythonCaller depending on the model
PythonCaller_Coordinate_remover
    PYTHONSYMBOL = FeatureProcessor
    PYTHONSOURCE:
      import fme
      import fmeobjects
      import numpy

      # Template Class Interface:
      # When using this class, make sure its name is set as the value of
      # the 'Class or Function to Process Features' transformer parameter
      class FeatureProcessor(object):
          def __init__(self):
              self.featureList = []

          def input(self,feature):
                  self.featureList.append(feature)

          def close(self):
              self.logger = fmeobjects.FMELogFile()
              for f in self.featureList:
                  # Depending on the model the range needs to be modified
                  coordIndex = range(1,5) # Here index 0,1,21 shall be removed
                  coordsIn = f.getAllCoordinates()
                  self.logger.logMessageString('PRINT')
                  self.logger.logMessageString(str(len(coordsIn)))
                  coordsOut = []
                  for i in coordIndex:
                      coordsOut.append(coordsIn[i])

                  tp = fmeobjects.FMELine(coordsOut)
                  tw = fmeobjects.FMEPolygon(tp)

                  nfw = fmeobjects.FMEFeature()
                  nfw.setGeometry(tw)

                  self.pyoutput(nfw)
    -> Generalizer
Generalizer
    ALG_TEXT = Douglas (Generalize)
    TOLERANCE = 600
    PRESERVE = No
    -> PythonCaller_Z_limit_adder
Dissolver__Rejected_: Inspector
SurfaceFootprintReplacer__Rejected_: Inspector

Bookmark: Calculation of building footprint area
  Depending on the construction of the building model the first floor may be sorted as floor 0 or 1, this is set with parameter First floor index.
FootprintAreaCalculator
    ELEVATION = @Value(Elevation)
    IFC_UNIQUE_ID = @Value(ifc_unique_id)
    IFC_PARENT_ID = @Value(ifc_parent_id)
    FloorIndex = 0
    IFC_PARENT_UNIQUE_ID = @Value(ifc_parent_unique_id)
    FootprintArea -> AreaComplianceCheck [Offsetter_Input]
    FootprintArea -> PythonCaller_Z_limit_adder_2

Bookmark: To SWEREF99 1330 coordinates
  Rotating, moving and scaling to get a roughly correct position of the building
Rotator_3
    ANGLE = -30
    YORIG = 0
    XORIG = 0
    ROTATED -> Scaler_3
Scaler_3
    XSCALE = 0.001
    TEXT_LOC_ONLY = Location and Size
    ZSCALE = 0.001
    YSCALE = 0.001
    RASTER_SCALING = Extents
    SCALE_ORIGIN = 0,0
    SCALED -> Offsetter_3
Offsetter_3
    ZOFF = 0
    MODE = Cartesian Coordinate
    YOFF = 6162760
    XOFF = 113830
    OFFSET -> BoundsExtractor_4
    OFFSET -> AttributeKeeper_2

Bookmark: Skapar attributen _upperCorner och _lowerCorner
  Only bounding box for datamängd in this case
BoundsExtractor_4
    YMIN = _ymin
    ZMIN = _zmin
    YMAX = _ymax
    ZMAX = _zmax
    XMIN = _xmin
    XMAX = _xmax
    -> AttributeRounder
AttributeRounder
    SRC_ATTRS = _ymin _zmax _ymax _xmin _xmax
    ROUND_TYPE = Nearest
    PLACES = $(decimalPlaces)
    -> StringConcatenator_13
StringConcatenator_13
    PARM_LINE = @Value(_ymax) @Value(_xmax)
    VAL_ATTR = _upperCorner
    ACTION = Create New Attribute
    -> StringConcatenator_14
StringConcatenator_14
    PARM_LINE = @Value(_ymin) @Value(_xmin)
    VAL_ATTR = _lowerCorner
    ACTION = Create New Attribute
    -> UUIDGenerator_BDM

Bookmark: Attribut-kopplingar
  Kopplar attribut från indata till Svensk geoprocess-attribut. Detaljer kring Svensk geoprocess-attributen finns bl.a. i UML-modellen för Byggnad: ftp://ftp.lantmateriet.se/pub/svensk_geoprocess/UML-modell/SvenskGeoprocess_HTML_modell/index.htm
Note: BY_ByggnadDatamängd
BY_BDM: AttributeCreator
    ATTR_TABLE:
      SET_TO _BDM_lowerCorner = @Value(_lowerCorner)
      SET_TO _BDM_upperCorner = @Value(_upperCorner)
      SET_TO _BDM_id_localId = @Value(_uuid_BDM)
      SET_TO _BDM_id_namespace = SGP.BY
      SET_TO _BDM_id_versionId = $(id_datamangd_versionId)
      SET_TO _BDM_uttagDatum = $(uttagDatum)
      SET_TO _BDM_metadata
      SET_TO _BDM_koordinatsystemPlan = $(koordinatsystemPlan)
      SET_TO _BDM_hojdsystem
      SET_TO _BDM_dimension = $(dimension)
    -> DateTimeConverter
Note: BY_Byggnad
BY_B: AttributeCreator
    ATTR_TABLE:
      SET_TO _B_lowerCorner = @Value(_lowerCorner)
      SET_TO _B_upperCorner = @Value(_upperCorner)
      SET_TO _B_id_localId = @Value(_uuid_B)
      SET_TO _B_id_namepace = SGP.BY
      SET_TO _B_id_versionId = $(id_byggnad_versionId)
      SET_TO _B_beginLifeSpanVersion
      SET_TO _B_endLifeSpanVersion
      SET_TO _B_byggnadNummer = $(byggnadNummer)
      SET_TO _B_byggnadAndamal = $(byggnadAndamal)
      SET_TO _B_byggnadNamn = $(byggnadNamn)
      SET_TO _B_status = $(status)
      SET_TO _B_bygglovAtgardTyp = $(bygglovAtgardTyp)
      SET_TO _B_bygglovStatusTyp = $(bygglovStatusTyp)
      SET_TO _B_beslutsdatum = $(beslutsdatum_bygglovStatus)
      SET_TO _B_atgardAr = $(atgardAr_bygglovstatus)
      SET_TO _B_byggnadArea = @Value(byggnadsArea)
      SET_TO _B_boArea
      SET_TO _B_byggnadKaraktar
      SET_TO _B_byggnadAnmarkning
      SET_TO _B_undantagenFranAdressattning
      SET_TO _B_ofriGrund = $(ofriGrund)
      SET_TO _B_externReferens
      SET_TO _B_cc_coClassId = $(coClassID)
      SET_TO _B_cc_coClassKod = $(coClassKod)
    -> StringConcatenator
    -> BY_B_Output
Note: BY_Byggnadsdel
BY_BD: AttributeCreator
    ATTR_TABLE:
      SET_TO _BD_lowerCorner = @Value(_lowerCorner)
      SET_TO _BD_upperCorner = @Value(_upperCorner)
      SET_TO _BD_byggnadNummerDel
      SET_TO _BD_byggnadAndamalDel
      SET_TO _BD_statusDel
      SET_TO _BD_bygglovStatusDel
      SET_TO _BD_antalVaningarOverMark
      SET_TO _BD_antalVaningarUnderMark
      SET_TO _BD_absolutHojd
      SET_TO _BD_relativHojd = @Value(relHojd)
      SET_TO _BD_boAreaDel
      SET_TO _BD_heltUnderMark
      SET_TO _BD_byggnadKaraktarDel
      SET_TO _BD_takTyp
      SET_TO _BD_geometriLoD0
      SET_TO _BD_geometri3DLoD1
      SET_TO _BD_lod2_geometri
      SET_TO _BD_lod2_ytgeometri
      SET_TO _BD_lod2_kropp = @Value(_geometri_BYD_2)
      SET_TO _BD_lod2_terrangskarning
      SET_TO _BD_lod2_lagesosakerhetPlan
      SET_TO _BD_lod2_lagesosakerhetHojd
      SET_TO _BD_lod2_matmetodPlan
      SET_TO _BD_lod2_matmetodHojd
      SET_TO _BD_lod2_geometriskUpplosning
      SET_TO _BD_lod2_flyghojd
      SET_TO _BD_lod2_skalaUnderlag
      SET_TO _BD_lod2_tidpunktMatning
      SET_TO _BD_lod2_osakertLage
      SET_TO _BD_lod2_osakertLageAnledning
      SET_TO _BD_lod2_ansvarigOrganisation
      SET_TO _BD_lod2_utforandeOrganisation
      SET_TO _BD_lod2_HMK_Standardniva
      SET_TO _BD_lod2_foljerMatningsanvisning
      SET_TO _BD_lod2_aktualitet
      SET_TO _BD_lod2_hojdLage3DBotten
      SET_TO _BD_lod2_planLageTyp
      SET_TO _BD_geometri3DLoD3
      SET_TO _BD_externReferens
      SET_TO _BD_cc_coClassId
      SET_TO _BD_cc_coClassKod
    -> Counter
Note: BY_Begransningsyta
BY_BY: AttributeCreator
    ATTR_TABLE:
      SET_TO _BY_lowerCorner
      SET_TO _BY_upperCorner
      SET_TO _BY_id_localId = @Value(_uuid_BY)
      SET_TO _BY_id_namespace = SGP.BY
      SET_TO _BY_id_versionId
      SET_TO _BY_beginLifespanVersion
      SET_TO _BY_endLifespanVersion
      SET_TO _BY_geometri = @Value(_geometri_surface)
      SET_TO _BY_geometriMetadata
      SET_TO _BY_externReferens
      SET_TO _BY_cc_coClassId
      SET_TO _BY_cc_coClassKod
    -> TestFilter_2
Note: BY_AggregeradByggnad
BY_AB: AttributeCreator [off]
    ATTR_TABLE:
      SET_TO _AB_lowerCorner
      SET_TO _AB_upperCorner
      SET_TO _AB_id_localId
      SET_TO _AB_id_namespace
      SET_TO _AB_id_versionId
      SET_TO _AB_beginLifespanVersion
      SET_TO _AB_endLifespanVersion
      SET_TO _AB_geometriAggregeradByggnad
      SET_TO _AB_externReferens
      SET_TO _AB_cc_coClassId
      SET_TO _AB_cc_coClassKod
Note: BY_FysiskByggnad
BY_FB: AttributeCreator [off]
    ATTR_TABLE:
      SET_TO _FB_lowerCorner
      SET_TO _FB_upperCorner
      SET_TO _FB_id_localId
      SET_TO _FB_id_namespace
      SET_TO _FB_id_versionId
      SET_TO _FB_beginLifespanVersion
      SET_TO _FB_endLifespanVersion
      SET_TO _FB_geometriFysiskByggnad
      SET_TO _FB_externReferens
      SET_TO _FB_cc_coClassId
      SET_TO _FB_cc_coClassKod
Note: BY_Byggnadstillbehör
BY_BT: AttributeCreator [off]
    ATTR_TABLE:
      SET_TO _BT_lowerCorner
      SET_TO _BT_upperCorner
      SET_TO _BT_id_localId
      SET_TO _BT_id_namespace
      SET_TO _BT_id_versionId
      SET_TO _BT_beginLifespanVersion
      SET_TO _BT_endLifespanVersion
      SET_TO _BT_byggnadstillbehor
      SET_TO _BT_status
      SET_TO _BT_lod0_punktgeometri
      SET_TO _BT_lod0_ytgeometri
      SET_TO _BT_lod0_lagesosakerhetPlan
      SET_TO _BT_lod0_lagesosakerhetHojd
      SET_TO _BT_lod0_matmetodPlan
      SET_TO _BT_lod0_matmetodHojd
      SET_TO _BT_lod0_geometriskUpplosning
      SET_TO _BT_lod0_flyghojd
      SET_TO _BT_lod0_skalaUnderlag
      SET_TO _BT_lod0_tidpunktMatning
      SET_TO _BT_lod0_osakertLage
      SET_TO _BT_lod0_osakertLageAnledning
      SET_TO _BT_lod0_ansvarigOrganisation
      SET_TO _BT_lod0_utforandeOrganisation
      SET_TO _BT_lod0_HMK_Standardniva
      SET_TO _BT_lod0_foljerMatningsanvisning
      SET_TO _BT_lod0_aktualitet
      SET_TO _BT_lod0_planLageTyp
      SET_TO _BT_lod0_hojdLageTyp
      SET_TO _BT_geometri3DLoD3
      SET_TO _BT_externReferens
      SET_TO _BT_cc_coClassId
      SET_TO _BT_cc_coClassKod
Note: BY_Oppning
BY_O: AttributeCreator [off]
    ATTR_TABLE:
      SET_TO _O_lowerCorner
      SET_TO _O_upperCorner
      SET_TO _O_id_localId
      SET_TO _O_id_namespace
      SET_TO _O_id_versionId
      SET_TO _O_beginLifespanVersion
      SET_TO _O_endLifespanVersion
      SET_TO _O_geometri
      SET_TO _O_geometriMetadata
      SET_TO _O_externReferens
      SET_TO _O_cc_coClassId
      SET_TO _O_cc_coClassKod

Bookmark: Skapar GML-ID
StringConcatenator_8
    PARM_LINE = @Value(_BDM_id_namespace).@Value(_BDM_id_localId)
    VAL_ATTR = _gml_id_BDM
    ACTION = Create New Attribute
    -> XMLTemplater [ROOT]
StringConcatenator
    PARM_LINE = @Value(_B_id_namepace).@Value(_B_id_localId)
    VAL_ATTR = _gml_id_B
    ACTION = Create New Attribute
    -> XMLTemplater_4 [ROOT]
StringConcatenator_12
    PARM_LINE = SGP.BY.@Value(_uuid_BYD)
    VAL_ATTR = _gml_id_BD
    ACTION = Create New Attribute
    -> XMLTemplater_4 [BY_BYGGNADSDEL]
StringConcatenator_11
    PARM_LINE = @Value(_BY_id_namespace).@Value(_BY_id_localId)
    VAL_ATTR = _gml_id_BYTY
    ACTION = Create New Attribute
    -> XMLTemplater [BY_TAKYTA]
StringConcatenator_10
    PARM_LINE = @Value(_BY_id_namespace).@Value(_BY_id_localId)
    VAL_ATTR = _gml_id_BYVY
    ACTION = Create New Attribute
    -> XMLTemplater [BY_VAGGYTA]

Bookmark: Skapar attributen _upperCorner och _lowerCorner
  Byggnad, not included in this version
BoundsExtractor_2
    YMIN = _ymin
    ZMIN = _zmin
    YMAX = _ymax
    ZMAX = _zmax
    XMIN = _xmin
    XMAX = _xmax
    -> AttributeRounder_3
Note: Round to two decimals
AttributeRounder_3
    SRC_ATTRS = _ymin _zmax _ymax _xmin _xmax
    ROUND_TYPE = Nearest
    PLACES = $(decimalPlaces)
    -> StringConcatenator_2
StringConcatenator_2
    PARM_LINE = @Value(_ymax) @Value(_xmax)
    VAL_ATTR = _upperCorner
    ACTION = Create New Attribute
    -> StringConcatenator_3
StringConcatenator_3
    PARM_LINE = @Value(_ymin) @Value(_xmin)
    VAL_ATTR = _lowerCorner
    ACTION = Create New Attribute
    -> UUIDGenerator_B

Bookmark: Extracting and adjusting geometry (Byggnadsdel)
  The string replaces replacing "&lt;" and "&lr;" with "<" and ">" from the XML templater
GeometryExtractor_2
    PREFER_POLYGON_OVER_SURFACE = No
    OMIT_NAMESPACES_DISPLAY = No
    ATTR = _geometri_BYD
    OGEOSMS_URL_PREFIX = http://maps.google.com/?q=
    KIND_LONG = GML v3.2.1
    OGCVERSION = 1.2
    REMOVE_GEOMETRY = No
    OGC_WKT_PRECISION_DISPLAY = Shortened 64-bit
    -> StringReplacer_6
StringReplacer_6
    SRC_ATTRS = _geometri_BYD
    NO_MATCH = _FME_NO_OP_
    FIND_TEXT = $(koordinatsystemPlan)
    CASE = NO
    REGEXP = NO
    REPLACE_TEXT = $(koordinatsystemPlanIdentifier)
    -> XMLTemplater_kropp [ROOT]
XMLTemplater_kropp
    ROOT_QUERY_EXPR:
      <by:kropp xmlns:by="http://namespace.lantmateriet.se/svenskgeoprocess/by/3.0">
          {fme:get-attribute("_geometri_BYD")}
      </by:kropp>
    VISIBLE_QUERY_VALIDATE = Yes
    RESULT_ATTRIBUTE = _geometri_BYD_2
    OUTPUT_XML_HEADER = No
    -> StringReplacer_4
StringReplacer_4
    SRC_ATTRS = _geometri_BYD_2
    NO_MATCH = _FME_NO_OP_
    FIND_TEXT = &lt;
    CASE = NO
    REGEXP = NO
    REPLACE_TEXT = <
    -> StringReplacer_5
StringReplacer_5
    SRC_ATTRS = _geometri_BYD_2
    NO_MATCH = _FME_NO_OP_
    FIND_TEXT = &gt;
    CASE = NO
    REGEXP = NO
    REPLACE_TEXT = >
    -> BoundsExtractor_3

Bookmark: Skapar attributen _upperCorner och _lowerCorner
  Byggnad, not included in this version
BoundsExtractor_3
    YMIN = _ymin
    ZMIN = _zmin
    YMAX = _ymax
    ZMAX = _zmax
    XMIN = _xmin
    XMAX = _xmax
    -> AttributeRounder_4
Note: Round to two decimals
AttributeRounder_4
    SRC_ATTRS = _ymin _zmax _ymax _xmin _xmax
    ROUND_TYPE = Nearest
    PLACES = $(decimalPlaces)
    -> StringConcatenator_4
StringConcatenator_4
    PARM_LINE = @Value(_ymax) @Value(_xmax)
    VAL_ATTR = _upperCorner
    ACTION = Create New Attribute
    -> StringConcatenator_5
StringConcatenator_5
    PARM_LINE = @Value(_ymin) @Value(_xmin)
    VAL_ATTR = _lowerCorner
    ACTION = Create New Attribute
    -> BY_BD

Bookmark: Genererar XML-fil (utbytesfil)
Note: Kopplar attribut till en / XML-kod. XML-koden har / genererats från schemat / BY_Byggnad.xsd och / består av BY_Byggnad / och BY_Byggnadsdel.
XMLTemplater_4
    ROOT_QUERY_EXPR:
      					<by:bestarAv xmlns:ad="http://inspire.ec.europa.eu/schemas/ad/4.0" xmlns:base="http://inspire.ec.europa.eu/schemas/base/3.3" xmlns:base2="http://inspire.ec.europa.eu/schemas/base2/2.0" xmlns:bu-base="http://inspire.ec.europa.eu/schemas/bu-base/4.0" xmlns:by="http://namespace.lantmateriet.se/svenskgeoprocess/by/3.0" xmlns:gco="http://www.isotc211.org/2005/gco" xmlns:ge="http://namespace.lantmateriet.se/svenskgeoprocess/base/ge/3.0" xmlns:gmd="http://www.isotc211.org/2005/gmd" xmlns:gml="http://www.opengis.net/gml/3.2" xmlns:gn="http://inspire.ec.europa.eu/schemas/gn/4.0" xmlns:gsr="http://www.isotc211.org/2005/gsr" xmlns:gss="http://www.isotc211.org/2005/gss" xmlns:gts="http://www.isotc211.org/2005/gts" xmlns:sg="http://namespace.lantmateriet.se/svenskgeoprocess/base/sg/3.0" xmlns:sgk="http://namespace.lantmateriet.se/svenskgeoprocess/base/sgk/3.0" xmlns:sgk1="http://namespace.lantmateriet.se/svenskgeoprocess/base/sgk/3.2" xmlns:xlink="http://www.w3.org/1999/xlink" xmlns:xml="http://www.w3.org/XML/1998/namespace" xmlns:xsi="http://www.w3.org/2001/XMLSchema-instance">
      						<by:BY_Byggnad gml:id="{fme:get-attribute("_gml_id_B")}">
      							<sg:id>
      								<base:localId>{fme:get-attribute("_B_id_localId")}</base:localId>
      								<base:namespace>{fme:get-attribute("_B_id_namepace")}</base:namespace>
                                      <base:versionId>{fme:get-attribute("_B_id_versionId")}</base:versionId>
      							</sg:id>
      							<sg:beginLifespanVersion xsi:nil="true" nilReason="unknown"/>
      							<by:byggnadNummer>{fme:get-attribute("_B_byggnadNummer")}</by:byggnadNummer>
                                  <by:byggnadAndamal>
                                      <by:byggnadAndamalTyp>{fme:get-attribute("_B_byggnadAndamal")}</by:byggnadAndamalTyp>
                                  </by:byggnadAndamal>
                                  <by:byggnadNamn>
                                      <sg:namn>{fme:get-attribute("_B_byggnadNamn")}</sg:namn>
                                      <sg:namnstatus>föreslaget namn</sg:namnstatus>
                                      <sg:sprak>svenska</sg:sprak>
                                      <sg:externalReference nilReason="unknown" xsi:nil="true"/>
                                  </by:byggnadNamn>
      							<by:status>{fme:get-attribute("_B_status")}</by:status>
                                  <by:bygglovStatus>
                                      <by:bygglovAtgardTyp>{fme:get-attribute("_B_bygglovAtgardTyp")}</by:bygglovAtgardTyp>
                                      <by:bygglovStatusTyp>{fme:get-attribute("_B_bygglovStatusTyp")}</by:bygglovStatusTyp>
                                      <by:beslutsdatum>{fme:get-attribute("_B_beslutsdatum")}</by:beslutsdatum>
                                      <by:atgardAr>{fme:get-attribute("_B_atgardAr")}</by:atgardAr>
                                  </by:bygglovStatus>
                                  { if( fme:has-attribute("byAreaExists") )
                                      then <by:byggnadArea>{fme:get-attribute("_B_byggnadArea")}</by:byggnadArea>
                                      else ()
                                  }
                                  <by:ofriGrund>{fme:get-attribute("_B_ofriGrund")}</by:ofriGrund>
                                  <by:coClass>
                                      <sg:coClassId>{fme:get-attribute("_B_cc_coClassId")}</sg:coClassId>
                                      <sg:coClassKod>{fme:get-attribute("_B_cc_coClassKod")}</sg:coClassKod>
                                  </by:coClass>
                                  {fme:process-features("BY_BYGGNADSDEL")}
      						</by:BY_Byggnad>
      					</by:bestarAv>
    VISIBLE_QUERY_VALIDATE = Yes
    BY_BYGGNADSDEL_QUERY_EXPR:

                                  <by:bestarAv>
                                      <by:BY_Byggnadsdel gml:id="{fme:get-attribute("_gml_id_BD")}">
                                          <by:byggnadNummerDel>{fme:get-attribute("_count_bd")}</by:byggnadNummerDel>
                                          <by:relativHojd>
                                              <by:hogstaHojdLageTyp>{fme:get-attribute("hogstaHojd")}</by:hogstaHojdLageTyp>
                                              <by:lagstaHojdLageTyp>{fme:get-attribute("lagstaHojd")}</by:lagstaHojdLageTyp>
                                              <by:hojdvarde>{fme:get-attribute("_BD_relativHojd")}</by:hojdvarde>
                                          </by:relativHojd>
                                          <by:heltUnderMark xsi:nil="true" nilReason="unknown"/>
                                          <by:geometri3DLoD2>
                                              {fme:get-attribute("_BD_lod2_kropp")}
                                              <by:geometriMetadata xsi:nil="true" nilReason="unknown"/>
      										<by:hojdLage3DBotten xsi:nil="true" nilReason="unknown"/>
      										<by:planLageTyp>{fme:get-attribute("planLageTyp")}</by:planLageTyp>
                                          </by:geometri3DLoD2>
                                      </by:BY_Byggnadsdel>
                                  </by:bestarAv>
    CONSECUTIVE_GROUPS = No
    RESULT_ATTRIBUTE = _XMLDelKod
    GROUP_BY = _uuid_BYD
    OUTPUT_XML_HEADER = No
    -> StringReplacer_7
StringReplacer_7
    SRC_ATTRS = _XMLDelKod
    NO_MATCH = _FME_NO_OP_
    FIND_TEXT = &lt;
    CASE = NO
    REGEXP = NO
    REPLACE_TEXT = <
    -> StringReplacer_8
StringReplacer_8
    SRC_ATTRS = _XMLDelKod
    NO_MATCH = _FME_NO_OP_
    FIND_TEXT = &gt;
    CASE = NO
    REGEXP = NO
    REPLACE_TEXT = >
    -> XMLTemplater [BY_BYGGNAD]
Note: Kopplar attribut till en / XML-kod. XML-koden har / genererats från schemat / BY_Byggnad.xsd.
XMLTemplater
    VISIBLE_QUERY_VALIDATE = Yes
    BY_BYGGNAD_QUERY_EXPR = {fme:get-attribute("_XMLDelKod")}
    BY_VAGGYTA_QUERY_EXPR:
      	<by:bestarAv>
      		<by:BY_Vaggyta gml:id="{fme:get-attribute("_gml_id_BYVY")}">
      			<sg:id>
      				<base:localId>{fme:get-attribute("_BY_id_localId")}</base:localId>
      				<base:namespace>{fme:get-attribute("_BY_id_namespace")}</base:namespace>
      			</sg:id>
      			<sg:beginLifespanVersion xsi:nil="true" nilReason="unknown"/>
      			<by:geometri>
          			{fme:get-attribute("_BY_geometri")}
      			</by:geometri>
      			<by:begransarByggnadsdel xlink:href="#SGP.BY.{fme:get-attribute('_uuid_BYD')}"/>
      		</by:BY_Vaggyta>
      	</by:bestarAv>
    OUTPUT_XML_HEADER = No
    ROOT_QUERY_EXPR:
      <?xml version="1.0" encoding="UTF-8"?>
      <by:BY_ByggnadDatamangd gml:id="{fme:get-attribute("_gml_id_BDM")}" xmlns:ad="http://inspire.ec.europa.eu/schemas/ad/4.0" xmlns:base="http://inspire.ec.europa.eu/schemas/base/3.3" xmlns:base2="http://inspire.ec.europa.eu/schemas/base2/2.0" xmlns:bu-base="http://inspire.ec.europa.eu/schemas/bu-base/4.0" xmlns:by="http://namespace.lantmateriet.se/svenskgeoprocess/by/3.0" xmlns:gco="http://www.isotc211.org/2005/gco" xmlns:ge="http://namespace.lantmateriet.se/svenskgeoprocess/base/ge/3.0" xmlns:gmd="http://www.isotc211.org/2005/gmd" xmlns:gml="http://www.opengis.net/gml/3.2" xmlns:gn="http://inspire.ec.europa.eu/schemas/gn/4.0" xmlns:gsr="http://www.isotc211.org/2005/gsr" xmlns:gss="http://www.isotc211.org/2005/gss" xmlns:gts="http://www.isotc211.org/2005/gts" xmlns:sg="http://namespace.lantmateriet.se/svenskgeoprocess/base/sg/3.0" xmlns:sgk="http://namespace.lantmateriet.se/svenskgeoprocess/base/sgk/3.0" xmlns:sgk1="http://namespace.lantmateriet.se/svenskgeoprocess/base/sgk/3.2" xmlns:xlink="http://www.w3.org/1999/xlink" xmlns:xml="http://www.w3.org/XML/1998/namespace" xmlns:xsi="http://www.w3.org/2001/XMLSchema-instance" xsi:schemaLocation="http://namespace.lantmateriet.se/svenskgeoprocess/by/3.0 http://namespace.lantmateriet.se/svenskgeoprocess/by/3.0/BY_Byggnad.xsd">
      	<gml:boundedBy>
      		<gml:Envelope srsName="urn:ogc:def:crs:EPSG::3008" srsDimension="2">
      			<gml:lowerCorner>{fme:get-attribute("_BDM_lowerCorner")}</gml:lowerCorner>
      			<gml:upperCorner>{fme:get-attribute("_BDM_upperCorner")}</gml:upperCorner>
      		</gml:Envelope>
      	</gml:boundedBy>
      	<sg:id>
      		<base:localId>{fme:get-attribute("_BDM_id_localId")}</base:localId>
      		<base:namespace>{fme:get-attribute("_BDM_id_namespace")}</base:namespace>
              <base:versionId>{fme:get-attribute("_BDM_id_versionId")}</base:versionId>
      	</sg:id>
      	<sg:uttagDatum>{fme:get-attribute("_BDM_uttagDatum")}</sg:uttagDatum>
      	<sg:koordinatsystemPlan>{fme:get-attribute("_BDM_koordinatsystemPlan")}</sg:koordinatsystemPlan>
      	<sg:dimension>{fme:get-attribute("_BDM_dimension")}</sg:dimension>
          {fme:process-features("BY_BYGGNAD")}
          {fme:process-features("BY_TAKYTA")}
          {fme:process-features("BY_VAGGYTA")}
      </by:BY_ByggnadDatamangd>
    BY_TAKYTA_QUERY_EXPR:
      	<by:bestarAv>
      		<by:BY_Takyta gml:id="{fme:get-attribute("_gml_id_BYTY")}">
      			<sg:id>
      				<base:localId>{fme:get-attribute("_BY_id_localId")}</base:localId>
      				<base:namespace>{fme:get-attribute("_BY_id_namespace")}</base:namespace>
      			</sg:id>
      			<sg:beginLifespanVersion xsi:nil="true" nilReason="unknown"/>
      			<by:geometri>
          			{fme:get-attribute("_BY_geometri")}
      			</by:geometri>
      			<by:begransarByggnadsdel xlink:href="#SGP.BY.{fme:get-attribute('_uuid_BYD')}"/>
      		</by:BY_Takyta>
      	</by:bestarAv>
    RESULT_ATTRIBUTE = _result
    -> StringReplacer
StringReplacer
    SRC_ATTRS = _result
    NO_MATCH = _FME_NO_OP_
    FIND_TEXT = &lt;
    CASE = NO
    REGEXP = NO
    REPLACE_TEXT = <
    -> StringReplacer_2
StringReplacer_2
    SRC_ATTRS = _result
    NO_MATCH = _FME_NO_OP_
    FIND_TEXT = &gt;
    CASE = NO
    REGEXP = NO
    REPLACE_TEXT = >
    -> XMLFormatter
XMLFormatter
    REMOVE_EMPTY_ELEMENT = No
    REPLACE_TABS_WITH_SPACES = no
    WHITESPACE_HANDLING = Preserve all whitespace
    SCHEMALOC_CLEANUP = No
    XML_OUTPUT_TYPE = Attribute
    XML_INPUT_TYPE = Attribute Specifying XML Text
    INDENT_SIZE = 1
    NAMESPACE_CLEANUP = Yes
    FORMATTING_CHOICE = Pretty-Print XML
    XML_ATTR_TEXT = _result
    LIST_NAME = _xml_error
    TEXT_INDENT = no
    OUTPUT_ENCODING = utf-8
    REMOVE_ALL_COMMENT = No
    XML_OUTPUT_ATTR = text_line_data
    COLLAPSE_EMPTY_ELEMENT = Yes
    PASSED -> HTTPCaller
Note: Hämtar schemat / BY_Byggnad.xsd / Version 3.0 från dess / plats på webben.
HTTPCaller
    VERIFY_SSL_CERTIFICATES = Yes
    TARGET_ATTR = _xml_schema
    SAVE_FILE = Attribute
    STATUS_CODE_ATTR = _http_status_code
    ERROR_ATTR = _error
    TARGET_ATTR_ENCODING = auto-detect
    FOLLOW_REDIRECTS = Yes
    TARGET_URL = http://namespace.lantmateriet.se/svenskgeoprocess/by/3.0/BY_Byggnad.xsd
    HTTP_METHOD = GET
    TRANSFER_TIMEOUT_LENGTH = 90
    CONNECTION_TIMEOUT_LENGTH = 60
    USE_COOKIES = No
    RESPONSE_HEADER_LIST_ATTR = _headers
    -> XMLValidator
Note: Validerar XML-filen / mot schemat.
XMLValidator
    SCHEMA_LOC = @Value(_xml_schema)
    XML_INPUT_TYPE = Attribute Specifying XML Text
    VAL_MODE_1 = Syntax and Schema
    LIST_NAME = _XML_schemafelmeddelande
    XML_ATTR_TEXT = text_line_data
    LIMIT_ERRORS = No
    PASSED -> text_line (writer TEXTLINE_1)
    PASSED -> XMLValidator_Passed
    FAILED -> XMLValidator_Failed_2
    FAILED -> text_line (writer TEXTLINE_1)
XMLValidator_Passed: Inspector
Note: Skriver ut koden till en XML-fil / med filändelsen *.xml
text_line (writer TEXTLINE_1)
    attributes: text_line_data buffer
Note: Inspektera fel i listan kallad / "_XML_schemafelmeddelande"
XMLValidator_Failed_2: Inspector

Bookmark: To create surfaces
PythonCaller_WallCreator_2
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.groundPoints = []

          def input(self,feature):
              self.groundPoints.append(feature)

          def close(self):
              # Looping over all building parts
              for byd in self.groundPoints:
                  roofHeight = float(byd.getAttribute('relHojd'))
                  uuidBYD = byd.getAttribute('_uuid_BYD')
                  po = byd.getGeometry()
                  cu = po.getBoundaryAsCurve()
                  li = cu.getAsLine()
                  points = li.getPoints()
                  coords = []
                  for co in points:
                      coords.append(co.getXYZ())

                  # Looping over the wall segments
                  for pos in xrange(len(coords)-1):
                      # Creating list with corner coords for current wall surface
                      tempPolyLineList = [coords[pos], coords[pos+1], (coords[pos+1][0], coords[pos+1][1], roofHeight), (coords[pos][0], coords[pos][1], roofHeight)]

                      tempPolyLine = fmeobjects.FMELine(tempPolyLineList)

                      tempWall = fmeobjects.FMEPolygon(tempPolyLine)

                      newFeatureWall = fmeobjects.FMEFeature()
                      newFeatureWall.setGeometry(tempWall)
                      newFeatureWall.setAttribute('_uuid_BYD', uuidBYD)
                      newFeatureWall.setAttribute('surfaceType', 'wall')
                      self.pyoutput(newFeatureWall)
    NEW_ATTRIBUTES = _uuid_BYD surfaceType
    -> UUIDGenerator_surfaces
Note: To "move" the footprint to roof height / to get a roof surface.
Offsetter_wallSurface
    ZOFF = @Value(relHojd)
    MODE = Cartesian Coordinate
    YOFF = 0
    XOFF = 0
    OFFSET -> AttributeCreator_surfaceType_roof_2
AttributeCreator_surfaceType_roof_2
    ATTR_TABLE = SET_TO surfaceType = roof
    -> UUIDGenerator_surfaces
UUIDGenerator_surfaces
    UUID_ATTR = _uuid_surface
    -> CoordinateSystemSetter_2

Bookmark: Check area
  Check calculated area against detailed development plan regulations
  Partly hard coded to specific placement (place/name of variable)
  Set an attribute AreaOk to Yes/No (True/False)
AreaComplianceCheck
    _AREA = @Value(_area)
    GML_PARENT_PROPERTY = @Value(gml_parent_property)
    zOffset2 = 20
    Tester_Passed -> Tester_Passed
Tester_Passed: Inspector

FME custom transformer BuildingHeightCheckerNew

2DForcer_buildingImport (input)
    -> 2DForcer_3
2DForcer_buildingImport_2 (input)
    -> HullAccumulator
DevelopmentPlan_Input (input)
    -> Junction_6
Note: Only to visualilse the 16 / elevation points.
FeatureColorSetter [off]
    COLOR = 0.666667,0,0
    MODE = Fixed
    FILL_COLOR = 0.666667,0,0
    COLORED -> FeatureColorSetter_Colored
FeatureColorSetter_Colored: Inspector [off]

Bookmark: Creating the horisontal plane representing mean ground elevation.
2DForcer_3
    2D -> BoundsExtractor
    2D -> HullAccumulator_2
AttributeKeeper_4
    KEEP_ATTRS = _angle,pointElevation,wallHeightOLD,_closest_candidate_x,_candidate_angle,_distance,_closest_base_x,wallHeightNEW,_closest_candidate_y,_closest_base_y,wallOrderID,zOffset
    -> Aggregator_2
    -> PythonCaller_GroundPointLifter
Note: Calculates mean ground elevation
PythonCaller_GroundPointLifter
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.pointList = []
              self.totElevation = 0
              self.elevOK = None

          def input(self,feature): # This function is called every time a feature is added
              if not feature.hasGeometry():
                  self.elevOK = feature.getAttribute('elevOK')
              else:
                  self.pointList.append(feature)
                  self.totElevation += feature.getAttribute('pointElevation')

          def close(self):
              if not self.elevOK:
                  print 'Elevation points are not including the highest and lowest points'
              else:
                  # Mean elevation of the ground around the building
                  meanElevation = self.totElevation*1.0/len(self.pointList)
                  # Iterating over all points and assigning z-value
                  for tempPoint in self.pointList:
                      tp = tempPoint.getGeometry()
                      tp.setZ(tempPoint.getAttribute('pointElevation'))
                      tempPoint.setGeometry(tp)
                      tempPoint.setAttribute('meanElevation', meanElevation)

                      self.pyoutput(tempPoint)
    NEW_ATTRIBUTES = meanElevation
    -> PointOnAreaOverlayer_2 [POINT]
    -> FeatureColorSetter
PointOnAreaOverlayer_2
    POLYS_FIRST = No
    ATTR_CONFLICT_RES = Use Original
    CANDIDATE_LIST_ATTRS_TO_INCLUDE_MODE = Selected Attributes
    OV_ATTR = _overlaps
    ATTR_ACCUM_MODE = Merge Incoming
    DEAGGREGATE_INPUT = Yes
    AREA -> Offsetter_3
Note: Lifting the plane to the mean ground level.
Offsetter_3
    ZOFF = @Value(meanElevation)
    MODE = Cartesian Coordinate
    YOFF = 0
    XOFF = 0
    OFFSET -> FeatureColorSetter_2
    <REJECTED> -> Offsetter_3__Rejected_
FeatureColorSetter_2
    COLOR = 0.666667,0,0
    MODE = Fixed
    FILL_COLOR = 0.666667,0,0
    COLORED -> PythonCaller_heightChecker
Offsetter_3__Rejected_: Inspector

Bookmark: Finding wall lenghts
  Calculates lenght of each side of the buidling
BoundsExtractor
    YMIN = _ymin
    ZMIN = _zmin
    YMAX = _ymax
    ZMAX = _zmax
    XMIN = _xmin
    XMAX = _xmax
    -> PythonCaller_EndPointFinder
PythonCaller_EndPointFinder
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.lineList = []

          def input(self,feature): # This function is called every time a feature is added
              self.lineList.append(feature)

          def close(self):

              # Iterating over all walls to keep endpoints only
              for wallLine in self.lineList:

                  xMax = wallLine.getAttribute('_xmax')
                  xMin = wallLine.getAttribute('_xmin')
                  yMax = wallLine.getAttribute('_ymax')
                  yMin = wallLine.getAttribute('_ymin')
                  inLine = wallLine.getGeometry() # We get the geometry as a face

                  # Have not found a way of checking what geometry type the area is
                  # so using try to see if it is donut och polygon
                  try:
                      # Only outer boundary is interesting (i.e. openings not relevant)
                      pl = inLine.getOuterBoundaryAsCurve()
                  except:
                      pl = inLine.getBoundaryAsCurve()

                  pointList = pl.getPoints()

                  candidatePoints = []

                  # Looping over all points in the list keeping only those that include one
                  # boundary coordinate as candidates. Other points cannot be endpoints.
                  for tempPoint in pointList:
                      tempXYZ = tempPoint.getXYZ()
                      if xMax == tempXYZ[0] or xMin == tempXYZ[0] or yMax == tempXYZ[1] or yMin == tempXYZ[1]: # No need to check ground level points

                          candidatePoints.append(tempPoint)


                  currentLen = 0

                  for startIndex in xrange(len(candidatePoints)):
                      tempStart = candidatePoints[startIndex]
                      for endIndex in xrange(len(candidatePoints)):
                          if not startIndex == endIndex:
                              tempend = candidatePoints[1]
                              tempLen = sqrt((tempStart.getXYZ()[0]-tempend.getXYZ()[0])**2 + (tempStart.getXYZ()[1]-tempend.getXYZ()[1])**2)
                              if tempLen > currentLen:
                                  currentLen = tempLen
                                  currentStartIndex = startIndex
                                  currentEndIndex = endIndex

                  newLine = fmeobjects.FMELine([candidatePoints[currentStartIndex].getXYZ(), candidatePoints[currentEndIndex].getXYZ()])

                  wallLine.setGeometry(newLine)

                  self.pyoutput(wallLine)
    -> LengthCalculator
LengthCalculator
    LEN_ATTR = _length
    DIM = 2
    MULT = 1
    -> PythonCaller_NumberOfLineSplits

Bookmark: Creating 16 points along the building walls used to derive mean ground elevation
Note: Calculates how many points to include for / each side of the building.
PythonCaller_NumberOfLineSplits
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.lineList = []
              self.totLen = 0
              self.nbrPoints = 16.0 # Number of points to calculate mean ground elevation

          def input(self,feature): # This function is called every time a feature is added
              self.lineList.append(feature)
              self.totLen += feature.getAttribute('_length')

          def close(self):

              lineFractions = []
              nbrPoints = []

              for wallLine in self.lineList:
                  lineFractions.append(wallLine.getAttribute('_length')/self.totLen)
                  # Number of line segments to split into
                  np = round(wallLine.getAttribute('_length')/self.totLen*self.nbrPoints)
                  nbrPoints.append(np)

                  # Creates points with a distance of half the DEM resolution to chekc that the highest and lowest
                  # elevation point is included among the points used to derived mean ground elevation.
                  npDense = round(wallLine.getAttribute('_length')/float(FME_MacroValues['DEM_resolution'])*2.0)

                  wallLine.setAttribute('nbrLines', np)
                  wallLine.setAttribute('nbrLinesDense', npDense)

                  self.pyoutput(wallLine)

              if sum(nbrPoints) != self.nbrPoints:
                  print 'WARNING!!!, number of line segments is not {}'.formatt(self.nbrPoints)
    NEW_ATTRIBUTES = nbrLines nbrLinesDense
    -> IterativeSnipper
    -> IterativeSnipper_2

Bookmark: Walls -> points
  Splits the walls of the building into lines (16 to calculate mean ground elevation) and replaces the lines with a point at the startpoint of the line. Start is used to get points at the corners of the buidling.
IterativeSnipper
    SNIPMODE = ToNumber
    SnipLength = @Value(nbrLines)
    -> LengthCalculator_2
LengthCalculator_2
    LEN_ATTR = _length
    DIM = 2
    MULT = 1
    -> Tester_2
Tester_2
    TEST_DESCRIPTION = ""
    TEST_CLAUSE = TEST @Value(_length) > 0.1
    BOOL_OP = OR
    TEST_MODE = Automatic
    PASSED -> CoordinateExtractor_3
CoordinateExtractor_3
    Y_ATTR = _yPoint
    IND = 0
    Z_ATTR = _zPoint
    X_ATTR = _xPoint
    MODE = Specify Coordinate
    -> PythonCaller_PointCreator
Note: Replaces the line geometries with / a point at the start point of the line.
PythonCaller_PointCreator
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.lineList = []

          def input(self,feature):
              self.lineList.append(feature)

          def close(self):
              for l in self.lineList:
                  # Reading coords of first point of the line
                  x = l.getAttribute('_xPoint')
                  y = l.getAttribute('_yPoint')
                  z = l.getAttribute('_zPoint')

                  newPoint = fmeobjects.FMEPoint(x, y, z)
                  l.setGeometry(newPoint)
                  self.pyoutput(l)
    -> NeighborFinder [BASE]

Bookmark: Finding max and min elevation for the dense points.
  Finding max and min elevation for the dense points (distance = halv DEM resolution) to confirm that the highest and lowest points in teh DEM around the buidling are included among the 16 points used to derive mean ground elevation.
IterativeSnipper_2
    SNIPMODE = ToNumber
    SnipLength = @Value(nbrLinesDense)
    -> LengthCalculator_3
LengthCalculator_3
    LEN_ATTR = _length
    DIM = 2
    MULT = 1
    -> Tester_3
Tester_3
    TEST_DESCRIPTION = ""
    TEST_CLAUSE = TEST @Value(_length) > 0.1
    BOOL_OP = OR
    TEST_MODE = Automatic
    PASSED -> CenterPointReplacer_3
CenterPointReplacer_3
    MODE = Center Point
    POINT -> NeighborFinder_2 [BASE]
from_DEM (input)
    -> CoordinateExtractor_2
CoordinateExtractor_2
    Y_ATTR = _y
    IND = 0
    Z_ATTR = _z
    X_ATTR = _x
    MODE = Specify Coordinate
    -> AttributeCreator_4
AttributeCreator_4
    ATTR_TABLE = SET_TO pointElevation = @Value(_z)
    -> AttributeKeeper_5
AttributeKeeper_5
    KEEP_ATTRS = pointElevation
    -> NeighborFinder_2 [CANDIDATE]
NeighborFinder_2
    MODE = Bases and Candidates
    MEASURES_FROM_CANDIDATE = Yes
    ATTR_CONFLICT_RES = Use Base
    INSERT_VERTEX = No
    MEASURE_TYPE = Continuous
    TREAT_POLYGON_AS = Lines
    K = 1
    CANDIDATES_FIRST = No
    ATTR_ACCUM_MODE = Merge Candidate
    MATCHED -> AttributeKeeper_6
    <REJECTED> -> NeighborFinder__Rejected__2
AttributeKeeper_6
    KEEP_ATTRS = _angle,pointElevation,wallHeightOLD,_closest_candidate_x,_candidate_angle,_distance,_closest_base_x,wallHeightNEW,_closest_candidate_y,_closest_base_y,wallOrderID,zOffset
    -> Aggregator_3
NeighborFinder__Rejected__2: Inspector

Bookmark: Plane for height visualisation
  Creating a plane extending with the buffer amount outside teh building. Used for visualisation of mean ground surface later.
HullAccumulator_2
    HULLTYPE_PARAM = Convex ()
    3DMODE_PARAM = 2D
    HULL -> Generalizer
Generalizer
    ALG_TEXT = Douglas (Generalize)
    TOLERANCE = 1
    PRESERVE = No
    -> Bufferer
Bufferer
    CAP_STYLE = None
    ANGLE = 22.5
    MITER_LIMIT = 3
    CORNER_STYLE = Miter
    OFFSET = 2
    BUFFERED -> PointOnAreaOverlayer_2 [AREA]

Bookmark: To find in which area the building is located
HullAccumulator
    HULLTYPE_PARAM = Convex ()
    3DMODE_PARAM = 2D
    HULL -> Clipper_3 [CLIPPER]
Note: Detailed plan areas
Junction_6
    -> Clipper_3 [CLIPPEE]
Clipper_3
    BOUNDARY_CASES = Treat as Inside
    LINES_AS_SEGMENTS = No
    CLIPPED_ATTR = _clipped
    ATTR_CONFLICT_RES = Use Clippee
    MISSING_VAL_MODE = Compute
    MEASURE_TYPE = Continuous
    CLIP_TYPE = Multiple Clippers
    PRESERVE_CLIPPEE_EXTENTS = No
    DEFAULT_VAL = 0
    VAL_SOURCE = Clippee Only
    CREATE_AGGREGATES = Yes
    CONNECT_Z_MODE = First Wins
    ATTR_ACCUM_MODE = Merge Clipper
    INSIDE -> PythonCaller_heightChecker

Bookmark: Checking min and max elevation
  Checking that the highest and lowest points are included with the 16 points used to find mean ground elevation.
Aggregator_3
    ORDERED = No
    MODE = Geometry - Assemble One Level
    ACCUM_ATTRS_NAME = Merge Incoming Attributes
    SEP = ,
    AGGREGATE_TYPE = Homogeneous Collection (If Possible)
    LIST_ATTRS_TO_INCLUDE = pointElevation
    LIST_NAME = pointElevationList
    AGGREGATE -> ListRangeExtractor_2
ListRangeExtractor_2
    MAX = _maxElevDense
    MIN = _minElevDense
    SRC_LIST = pointElevationList{}.pointElevation
    -> PythonCaller_GroundPointLifter_2
Aggregator_2
    ORDERED = No
    MODE = Geometry - Assemble One Level
    ACCUM_ATTRS_NAME = Merge Incoming Attributes
    SEP = ,
    AGGREGATE_TYPE = Homogeneous Collection (If Possible)
    LIST_ATTRS_TO_INCLUDE = pointElevation
    LIST_NAME = pointElevationList
    AGGREGATE -> ListRangeExtractor
ListRangeExtractor
    MAX = _maxElev
    MIN = _minElev
    SRC_LIST = pointElevationList{}.pointElevation
    -> PythonCaller_GroundPointLifter_2
Note: Checks that the min and max / elevations are included with / the 16 points.
PythonCaller_GroundPointLifter_2
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.pointList = []
              self.pointListDense = []


          def input(self,feature): # This function is called every time a feature is added
              if feature.getAttribute('_minElevDense'):
                  self.pointListDense.append(feature)
              elif feature.getAttribute('_minElev'):
                  self.pointList.append(feature)

          def close(self):
              # Checking that min and max elevations are included in the 16 points
              minElevDiff = float(self.pointList[0].getAttribute('_minElev')) - float(self.pointListDense[0].getAttribute('_minElevDense'))
              maxElevDiff = float(self.pointList[0].getAttribute('_maxElev')) - float(self.pointListDense[0].getAttribute('_maxElevDense'))

              # Creating a new feature with the attribute elevOK with the value True if highest
              # and lowest points of teh building are included in the 16 points.
              nf = fmeobjects.FMEFeature()
              if abs(minElevDiff) < 0.01 and abs(maxElevDiff) < 0.01:
                  nf.setAttribute('elevOK', True)
              else:
                  nf.setAttribute('elevOK', False)

              self.pyoutput(nf)
    NEW_ATTRIBUTES = elevOK
    -> PythonCaller_GroundPointLifter

Bookmark: Getting elevation for the 16 points along the buildiing walls.
from_DEM_2 (input)
    -> CoordinateExtractor
CoordinateExtractor
    Y_ATTR = _y
    IND = 0
    Z_ATTR = _z
    X_ATTR = _x
    MODE = Specify Coordinate
    -> AttributeCreator_3
AttributeCreator_3
    ATTR_TABLE = SET_TO pointElevation = @Value(_z)
    -> AttributeKeeper_3
AttributeKeeper_3
    KEEP_ATTRS = pointElevation
    -> NeighborFinder [CANDIDATE]
NeighborFinder
    MODE = Bases and Candidates
    MEASURES_FROM_CANDIDATE = Yes
    ATTR_CONFLICT_RES = Use Base
    INSERT_VERTEX = No
    MEASURE_TYPE = Continuous
    TREAT_POLYGON_AS = Lines
    K = 1
    CANDIDATES_FIRST = No
    ATTR_ACCUM_MODE = Merge Candidate
    MATCHED -> AttributeKeeper_4
    <REJECTED> -> NeighborFinder__Rejected_
NeighborFinder__Rejected_: Inspector

Bookmark: Checking if the building heigth is allowed according to the development plan.
  Checks the building height against the development plan and displays the ground elevation plane. 
  If the building is too high, a horisontal plane representing max allowed building height is visualised.
Note: Checks if building height is allowed. / Adds the attribute heightOK with the / value True or False.
PythonCaller_heightChecker
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.byggnad = []
              self.maxByggnadsHojd = None

          def input(self,feature): # This function is called every time a feature is added
              if feature.getAttribute('gml_parent_property') == 'egenskapsbestammelse':
                  self.maxByggnadsHojd = float(feature.getAttribute('byggnadshojd'))
              elif feature.getAttribute('wallHeightNEW'):
                  self.byggnad.append(feature)


          def close(self):

              for by in self.byggnad:

                  wallTop = int(by.getAttribute('wallHeightNEW'))*0.001 + float(by.getAttribute('zOffset'))

                  buildingHeight = wallTop - by.getAttribute('meanElevation')

                  # Checing if the building is lower than the allowed height with the
                  # allowed toleracne of 10 cm.
                  if buildingHeight - self.maxByggnadsHojd < 0.1:
                      by.setAttribute('heightOK', True)
                  else:
                      by.setAttribute('heightOK', False)
                      nf = by.clone()
                      geo = nf.getGeometry()
                      nl = geo.getBoundaryAsCurve()
                      np = nl.getPoints()

                      # Horisontal surface so we can take z from any point
                      newZ = np[0].getXYZ()[2] + self.maxByggnadsHojd
                      # new pointlist with coordinates lifted to max building height
                      [p.setZ(newZ) for p in np]
                      liftedXYZ = [p.getXYZ() for p in np]
                      liftedLine = fmeobjects.FMELine(liftedXYZ)
                      liftedPoly = fmeobjects.FMEPolygon(liftedLine)
                      nf.setGeometry(liftedPoly)
                      nf.setAttribute('maxHeight', 'True')
                      self.pyoutput(nf)

                  self.pyoutput(by)
    NEW_ATTRIBUTES = heightOK maxHeight
    -> TestFilter_6
TestFilter_6
    DEFAULT_VALUE = <UNFILTERED>
    TEST_LIST = BOOL_OP,OR,COMPOSITE_TEST,<Unused>,TEST_CLAUSE,"TEST @Value(maxHeight) = True",maxHeight
    maxHeight -> maxHeight_if_too_high (output)
    <UNFILTERED> -> groundElevation (output)
maxHeight_if_too_high (output)
groundElevation (output)

FME custom transformer LineDirectionChanger

Parameters:
- _VY = @Value(_vy)   # Vy
- _X_END_WALL = @Value(_x_end_wall)   # X End Wall
- _X_START_WALL = @Value(_x_start_wall)   # X Start Wall
- _VX = @Value(_vx)   # Vx
- _Y_END_WALL = @Value(_y_end_wall)   # Y End Wall
- _Y_START_WALL = @Value(_y_start_wall)   # Y Start Wall

AttributeCreator_2_Input (input)
    -> AttributeCreator_2
AttributeCreator_2
    ATTR_TABLE:
      SET_TO x_norm = @Evaluate(@Value(_y_start_wall)-@Value(_y_end_wall))
      SET_TO y_norm = @Evaluate(@Value(_x_end_wall)-@Value(_x_start_wall))
    -> AttributeCreator_3
AttributeCreator_3
    ATTR_TABLE:
      SET_TO dir_change_x = @Evaluate(@Value(x_norm)*@Value(_vx))
      SET_TO dir_change_y = @Evaluate(@Value(y_norm)*@Value(_vy))
    -> TestFilter_2
TestFilter_2
    DEFAULT_VALUE = <UNFILTERED>
    TEST_LIST:
      BOOL_OP,OR,COMPOSITE_TEST,<Unused>,TEST_CLAUSE,"TEST @Value(dir_change_x) < 0
      TEST @Value(dir_change_y) < 0",change_direction
    change_direction -> Orientor
    <UNFILTERED> -> AttributeRenamer
Orientor
    KIND = REVERSE
    FLIP_APPEARANCES_CHOICE = Yes
    ORIENTED -> AttributeCreator
Note: Reversing also attributes
AttributeCreator
    ATTR_TABLE:
      SET_TO _start_x = @Value(_x_end_wall)
      SET_TO _end_x = @Value(_x_start_wall)
      SET_TO _start_y = @Value(_y_end_wall)
      SET_TO _end_y = @Value(_y_start_wall)
    -> AttributeRemover_3
Note: Need to rename start and end attributes. / For reversed lines these are handled by the / AttributeCreator after the Orientor
AttributeRenamer
    ATTR_TABLE:
      RENAME_SET_DEFAULT _x_start_wall > _start_x
      RENAME_SET_DEFAULT _y_start_wall > _start_y
      RENAME_SET_DEFAULT _x_end_wall > _end_x
      RENAME_SET_DEFAULT _y_end_wall > _end_y
    -> AttributeRemover_3
AttributeRemover_3
    REMOVE_ATTRS = Name,_y_end_wall,ifc_unique_id,_z_end_wall,_z_start_wall,Description,_x_start_wall,ObjectType,_y_start_wall,Tag,_x_end_wall,y_norm,x_norm,ifc_parent_id,ifc_parent_unique_id
    -> AttributeRemover_3_Output (output)
AttributeRemover_3_Output (output)

FME custom transformer IterativeSnipper
This transformer can be used to snip a line into shorter lines by specifying a segment length or number of output lines.
Input Ports
    Input
Any feature with line geometry.
    Output Ports
    Output
Line features are output. Number of features depends on User Parameters.
    <Rejected>
Features are rejected if they do not have line geometry. The value INVALID_GEOMETRY_TYPE is stored in the fme_rejection_code attribute.
    Parameters
    Snipping Mode
Shorten to Length: Input line will be iteratively cut into lines of desired length. In this mode, a line will be cut into shorter lines until the length becomes smaller than desired length. The short segment will also be output.
Divide into Number of Lines: Input line will be snipped into a desired number of lines with equal lengths.

Parameters:
- SNIPMODE = ToLength   # Shorten to Length,ToLength%Divide into Number of Lines,ToNumber Snipping Mode
- SnipLength = 20   # Value

Input (input)
    -> GeometryFilter
Note: Filter out all geometries / except lines.
GeometryFilter
    GEOM_PORT_NAMES = Line
    BREAK_AGG = No
    LINE -> LengthCalculator
    <UNFILTERED> -> AttributeCreator
Note: Calculate length / of input line.
LengthCalculator
    LEN_ATTR = Iterative_Snipper_length
    DIM = 3
    MULT = 1
    -> Snip_Mode
Note: Determine Snipping Mode
Snip_Mode: Tester
    TEST_DESCRIPTION = ""
    TEST_CLAUSE = TEST $(SNIPMODE) = ToNumber
    BOOL_OP = OR
    TEST_MODE = Automatic
    PASSED -> ExpressionEvaluator
    FAILED -> ParameterFetcher
AttributeCreator
    ATTR_TABLE = SET_TO fme_rejection_code = INVALID_GEOMETRY_TYPE
    -> <Rejected> (output)
<Rejected> (output)
LoopINPUT (input)
    -> LengthCalculator_2
Note: Calculate length / of input line segment.
LengthCalculator_2
    LEN_ATTR = Iterative_Snipper_length
    DIM = 3
    MULT = 1
    -> Tester
Note: If line's length is less than / or equal to Snipping Distance, / send to Output. If not, snip it.
Tester
    TEST_DESCRIPTION = ""
    TEST_CLAUSE = TEST @Value(Iterative_Snipper_length) <= @Value(Iterative_Snipper_maxLength)
    BOOL_OP = OR
    TEST_MODE = Automatic
    TEST_LIST = &_length,>,&_maxLength
    PASSED -> AttributeRemover
    FAILED -> Snipper_3
Note: Cut a segment with length / of snipping distance from / the beginning of the line, / output the segment to the / output port, send the rest of the / line to the looping Output port.
Snipper_3
    STARTLOCATIONATTR = 0
    SNIPMODE = Distance (Value)
    MEASUREMENTTYPE = 3D
    ENDLOCATIONATTR = @Value(Iterative_Snipper_maxLength)
    -> AttributeRemover
    REMNANTS -> LoopINPUT (output)
Note: Clean up attributes
AttributeRemover
    REMOVE_ATTRS = Iterative_Snipper_length,Iterative_Snipper_maxLength
    -> Output (output)
Output (output)
LoopINPUT (output)

Bookmark: Determine Snipping Distance
ExpressionEvaluator
    VAL_ATTR = Iterative_Snipper_maxLength
    ACTION = Create New Attribute
    EXPRESSION = @Value(Iterative_Snipper_length)/@double($(SnipLength))
    -> Tester
ParameterFetcher
    ATTR_LIST = Iterative_Snipper_maxLength {$(SnipLength)}
    -> Tester

FME custom transformer OuterWallSegmentFinder

Parameters:
- _UUID = @Value(_uuid)   # Uuid
- INTERSECTLINE = @Value(IntersectLine)   # IntersectLine

Intersector_line_walls_Input (input)
    -> Intersector_line_walls
Note: Intersecting imaginary line with walls to / find one outer wall.
Intersector_line_walls
    SEG_ATTR = _segments
    SEPARATE_COLLINEAR_SEGMENTS = No
    DUPLICATE_Z_NODES = No
    GENERATE_LIST_DROP = NO
    OV_ATTR = _overlaps
    MEASURE_TYPE = Continuous
    ATTRS_ACCUM_MODE = Merge Attributes
    PERFORM_SELF_INTERSECTION = No
    DEAGGREGATE_INPUT = Yes
    NODE -> TestFilter
    <REJECTED> -> Intersector_line_walls__Rejected_
Intersector_line_walls__Rejected_: Inspector
Note: To find the nodes that belong to the test line
TestFilter
    DEFAULT_VALUE = <UNFILTERED>
    TEST_LIST = BOOL_OP,OR,COMPOSITE_TEST,<Unused>,TEST_CLAUSE,"TEST @Value(IntersectLine) = line",CandidateNode
    CandidateNode -> CoordinateExtractor
CoordinateExtractor
    Y_ATTR = _y
    IND = 0
    Z_ATTR = _z
    X_ATTR = _x
    MODE = Specify Coordinate
    -> Sorter
Sorter
    SORT_PARM = _x NUMERIC DESCENDING
    SORTED -> Counter
Counter
    SCOPE = Local
    CNT_ATTR = _count
    DOMAIN = counter
    START = 0
    -> Tester
Tester
    TEST_CLAUSE = NUM_TEST @Value(_count) = 1
    BOOL_OP = OR
    TEST_MODE = Automatic
    PASSED -> FeatureMerger [REQUESTOR]
FeatureMerger_Supplier (input)
    -> FeatureMerger [SUPPLIER]
Note: The merged feature / is one outer wall
FeatureMerger
    REJECT_NULL_MISSING_KEYS = No
    PROCESS_DUPS = No
    ATTR_CONFLICT_RES = Use Requestor
    MERGE_TYPE = Attributes and Geometry
    JOIN_KEYS = @Value(_uuid) @Value(_uuid) AUTO
    SUPPLIERS_FIRST = No
    IGNORE_NULLS = No
    ATTR_ACCUM_MODE = Merge Supplier
    MERGED -> FeatureMerger_Merged (output)
FeatureMerger_Merged (output)

FME custom transformer Protruding_Part

Parameters:
- _ZMINVAL = @Value(_zminval)   # Zminval
- OFFSET = 500   # Buffer Amount
- DISTANCE = 3000   # Distance
- _ZMIN = @Value(_zmin)   # Zmin

Bufferer_Input (input)
    -> Bufferer
Clipper_Byggnad (input)
    -> Clipper [CLIPPEE]
Clipper
    BOUNDARY_CASES = Treat as Inside
    LINES_AS_SEGMENTS = No
    CLIPPED_ATTR = _clipped
    ATTR_CONFLICT_RES = Use Clippee
    MISSING_VAL_MODE = Compute
    MEASURE_TYPE = Continuous
    CLIP_TYPE = Multiple Clippers
    PRESERVE_CLIPPEE_EXTENTS = No
    DEFAULT_VAL = 0
    VAL_SOURCE = Clippee Only
    CREATE_AGGREGATES = Yes
    CONNECT_Z_MODE = First Wins
    ATTR_ACCUM_MODE = Merge Clipper
    INSIDE -> Output_Inside (output)
    OUTSIDE -> GeometryValidator
    <REJECTED> -> Clipper__Rejected_
Output_Inside (output)
Note: Kontrollera så att objekten har geometri
GeometryValidator
    SUMMARY = Detailed
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    ORIENTATION_CHECK_DIR = Valid
    AREA_ORIENTATION = AREA_ORIENTATION
    NULL_REMOVAL = NULL_REMOVAL
    ISSUE_ATTR_NAME = _issues
    NAN_REMOVAL = NAN_REMOVAL
    CONNECT_Z_MODE_TR = First Wins
    PRESETS = Basic Geometry Integrity
    TYPE_REPAIR = TYPE_REPAIR
    REPAIR = Yes
    ARC_ENDPOINT_TOLERANCE_MODE = Auto
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    CAP_STYLE = Round
    ANGLE = 1
    CORNER_STYLE = Round
    OFFSET = $(OFFSET)
    BUFFERED -> SurfaceFootprintReplacer
    BUFFERED -> Bufferer_Buffered
Bufferer_Buffered: Inspector [off]
SurfaceFootprintReplacer
    OFFSET_Z = @Value(_zminval)
    SHADOW_MODE = Overhead Shadow
    FOOTPRINT -> Extruder
Note: Extrude 3 el 2 m
Extruder
    DISTANCE = $(DISTANCE)
    DIRECTION = Auto
    EXTRUDED -> Clipper [CLIPPER]
    <REJECTED> -> Extruder__Rejected_
Extruder__Rejected_: Inspector

FME custom transformer NormalVectorFinder

CoordinateExtractor_Input (input)
    -> CoordinateCounter
Note: Note that there are wall surfaces (beloning to "Takplan" in KTH where index 0 is in a vertical line with both first and second last index ont eh line i.e. the normals arr not correct.
NormVec_Output (output)

Bookmark: Calculate Normal Vector (_vx, _vy, _vz)
  There was a special case with one outer wall surface (see notes) which gave wrong orientation due to concave shape. This version is using coordinates with index 0, 1, (nbr coords -4) to test if that solves the problem. See notes for more details.
Note: Need to know the number of / coordinates to find the second / last.
CoordinateCounter
    CNT_ATTR = _coordcount_normal_vector
    -> CoordinateExtractor_7
CoordinateExtractor_7
    Y_ATTR = _y0
    IND = 0
    Z_ATTR = _z0
    X_ATTR = _x0
    Z_DEFAULT = -9999
    -> CoordinateExtractor_8
Note: Should be index 1 and that works fine with FME2017 but for some reason 1 is not a valid index with FME2018.1. Index 2 seems to work fine though......
CoordinateExtractor_8
    Y_ATTR = _y1
    IND = 1
    Z_ATTR = _z1
    X_ATTR = _x1
    Z_DEFAULT = -9999
    -> CoordinateExtractor_9
CoordinateExtractor_9
    Y_ATTR = _y2
    IND = @Value(_coordcount_normal_vector)-2
    Z_ATTR = _z2
    X_ATTR = _x2
    Z_DEFAULT = -9999
    -> AttributeCreator_5
AttributeCreator_5
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_6
AttributeCreator_6
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))
    -> AttributeRemover
AttributeRemover
    REMOVE_ATTRS = _coordcount_normal_vector
    -> NormVec_Output (output)

Bookmark: Calculate Normal Vector (_vx, _vy, _vz)
CoordinateExtractor
    Y_ATTR = _y0
    IND = 0
    Z_ATTR = _z0
    X_ATTR = _x0
    Z_DEFAULT = -9999
    -> CoordinateExtractor_2
CoordinateExtractor_2
    Y_ATTR = _y1
    IND = 1
    Z_ATTR = _z1
    X_ATTR = _x1
    Z_DEFAULT = -9999
    -> CoordinateExtractor_3
CoordinateExtractor_3
    Y_ATTR = _y2
    IND = 3
    Z_ATTR = _z2
    X_ATTR = _x2
    Z_DEFAULT = -9999
    -> AttributeCreator
AttributeCreator
    ATTR_LIST = _vx0,@Evaluate(@Value(_x1)-@Value(_x0)),_vy0,@Evaluate(@Value(_y1)-@Value(_y0)),_vz0,@Evaluate(@Value(_z1)-@Value(_z0)),_vx1,@Evaluate(@Value(_x2)-@Value(_x0)),_vy1,@Evaluate(@Value(_y2)-@Value(_y0)),_vz1,@Evaluate(@Value(_z2)-@Value(_z0))
    -> AttributeCreator_2
AttributeCreator_2
    ATTR_LIST = _vx,@Evaluate(@Value(_vy0)*@Value(_vz1)-@Value(_vz0)*@Value(_vy1)),_vy,@Evaluate(@Value(_vz0)*@Value(_vx1)-@Value(_vx0)*@Value(_vz1)),_vz,@Evaluate(@Value(_vx0)*@Value(_vy1)-@Value(_vy0)*@Value(_vx1))

FME custom transformer FootprintAreaCalculator

Parameters:
- IFC_PARENT_UNIQUE_ID = @Value(ifc_parent_unique_id)   # Ifc Parent Unique Id
- IFC_UNIQUE_ID = @Value(ifc_unique_id)   # ifc_unique_id
- ELEVATION = @Value(Elevation)   # Elevation
- IFC_PARENT_ID = @Value(ifc_parent_id)   # Ifc Parent Id
- FloorIndex = 1   # First floor index

All_ListBasedFeatureMerger (input)
    -> ListBasedFeatureMerger [SUPPLIER]
IfSlab_Input (input)
    -> StoreyIndexFinder_2 [AttributeCreator_StoreyList_Input]
BuildingStorey_AggregatedList (input)
    -> StoreyIndexFinder_2 [PythonCaller_2_Input]
StoreyIndexFinder_2
    storeyIndex = $(FloorIndex)
    IFC_UNIQUE_ID = @Value(ifc_unique_id)
    Tester_StoreyIndex_Passed -> StoreyIndexFinder_FirstFloor
    Tester_StoreyIndex_Passed -> CreateBasisBYA [Input_storey]
StoreyIndexFinder_FirstFloor: Inspector
Note: Clip the building to be able to find the protruding parts.
Clipper_Max_3m_Input (input)
    -> Clipper_Max_3m_2
Clipper_Max_5m_Input (input)
    -> Clipper_Max_5m_3
Clipper_BottomEdge_Input (input)
    -> Clipper_BottomEdge_2
Note: Clip lowest part of the wall
Clipper_BottomEdge_2: Building_Clipper
    OFFSET_Z = @Value(Elevation)
    DISTANCE = 10
    IFC_PARENT_UNIQUE_ID = @Value(ifc_parent_unique_id)
    Output_extruded -> PointCloudClipper [Clipper]
    Output_clipper -> CreateBasisBYA [Input_facade]
    Rejected -> PointCloudClipper [Wall]
Note: Handle wall objects that won't clip with default FME Clipper
PointCloudClipper
    IFC_UNIQUE_ID = @Value(ifc_unique_id)
    IFC_PARENT_UNIQUE_ID = @Value(ifc_parent_unique_id)
    Output_2D -> CreateBasisBYA [Input_pointCloud]
CreateBasisBYA
    IFC_UNIQUE_ID = @Value(ifc_unique_id)
    -> AttributeManager_2
    -> Protruding_Part [Bufferer_Input]
    -> SurfaceFootprintReplacer_3
SurfaceFootprintReplacer_3
    OFFSET_Z = 0
    SHADOW_MODE = Overhead Shadow
    FOOTPRINT -> Snapper
Note: Calculate BUA, / scale from mm2 to m2
AreaCalculator
    AREA_ATTR = _area
    AREA_TYPE = Plane Area
    MULT = 1/1000000
    -> AttributeRounder
Note: Round to on dec.
AttributeRounder
    SRC_ATTRS = _area
    ROUND_TYPE = Nearest
    PLACES = 1
    -> AttributeKeeper_2
AttributeKeeper_2
    KEEP_ATTRS = _area
    -> FootprintArea (output)
FootprintArea (output)

Bookmark: Klipper byggnaden 0-3 m
Clipper_Max_3m_2: Building_Clipper
    OFFSET_Z = @Value(Elevation)
    DISTANCE = 3000
    IFC_PARENT_UNIQUE_ID = @Value(ifc_parent_unique_id)
    Output_extruded -> PointCloudClipper_5 [Clipper]
    Output_clipper -> Protruding_Part [Clipper_Byggnad]
    Rejected -> PointCloudClipper_5 [Wall]
PointCloudClipper_5
    IFC_UNIQUE_ID = @Value(ifc_unique_id)
    IFC_PARENT_UNIQUE_ID = @Value(ifc_parent_unique_id)
    Output_3D -> Protruding_Part [Clipper_Byggnad]

Bookmark: Klipper byggnaden 3-5 m
Clipper_Max_5m_3: Building_Clipper
    OFFSET_Z = @Value(Elevation)+3000
    DISTANCE = 2000
    IFC_PARENT_UNIQUE_ID = @Value(ifc_parent_unique_id)
    Output_extruded -> PointCloudClipper_6 [Clipper]
    Output_clipper -> Protruding_Part_2 [Clipper_Byggnad]
    Rejected -> PointCloudClipper_6 [Wall]
PointCloudClipper_6
    IFC_UNIQUE_ID = @Value(ifc_unique_id)
    IFC_PARENT_UNIQUE_ID = @Value(ifc_parent_unique_id)
    Output_3D -> Protruding_Part_2 [Clipper_Byggnad]

Bookmark: 0-3m, < 0,5m
Protruding_Part
    _ZMIN = @Value(_zmin)
    DISTANCE = 3000
    _ZMINVAL = @Value(_zminval)
    OFFSET = 500
    Output_Outside -> Aggregator

Bookmark: 3-5m, < 1,5m
Note: Flytta zmin +3000mm
AttributeManager_2
    ATTR_TABLE:
      SET_TO _zminval = @Value(_zminval)+3000
      SET_TO _zmin = +3000
    -> Protruding_Part_2 [Bufferer_Input]
Protruding_Part_2
    _ZMIN = @Value(_zmin)
    DISTANCE = 2000
    _ZMINVAL = @Value(_zminval)
    OFFSET = 1500
    Output_Outside -> Aggregator

Bookmark: Protruding parts
Note: Clip protruding parts (Output_Outside)
Aggregator
    ORDERED = No
    MODE = Attributes Only
    ACCUM_ATTRS_NAME = Merge Incoming Attributes
    SEP = ,
    CONCAT_ATTRS = ifc_unique_id
    LIST_ATTRS_TO_INCLUDE = ifc_unique_id
    LIST_NAME = ListName
    AGGREGATE -> ListElementCounter
ListElementCounter
    CNT_ATTR = nbrStoreys
    LIST_NAME = ListName{}
    -> ListBasedFeatureMerger [REQUESTOR]
Note: Retrive the whole protruding object with ifc_unique_id, project and merge with "BasisBUA"
ListBasedFeatureMerger
    MODE = AUTO
    REFEEATTR = @Value(ifc_unique_id)
    PROCESS_DUPS = Yes
    REFERATTR = ListName{}.ifc_unique_id
    MERGE_TYPE = Geometry
    GEOM_TYPE = Build Aggregates
    BUILD_INCOMPLETE = Merge Supplier Information
    MERGED -> SurfaceFootprintReplacer_2
SurfaceFootprintReplacer_2
    OFFSET_Z = 0
    SHADOW_MODE = Overhead Shadow
    FOOTPRINT -> Snapper
Dissolver_2
    ACCUM_INPUT_ATTRS = Use Attributes From One Feature
    NO_OVRLP = No
    CONNECT_Z_MODE = First Wins
    DEAGGREGATE_INPUT = Yes
    AREA -> AreaCalculator

Bookmark: Prepare for dissolve
  Snapp areas that won't dissolve (because they don't intersect/ are connected)
Snapper
    SNAPTYPE_PARAM = Segment Snapping
    TOLERANCE = 10
    CLEANING_TOLERANCE_MODE = AUTO
    SNAPPED -> Dissolver_2
    UNTOUCHED -> Dissolver_2

FME custom transformer mainWallFinder

Parameters:
- WALLHEIGHTNEW = @Value(wallHeightNEW)   # wallHeightNEW
- WALLHEIGHTOLD = @Value(wallHeightOLD)   # wallHeightOLD
- WALLORDERID = @Value(wallOrderID)   # wallOrderID

Note: Wall surfaces from the building
inputWalls (input)
    -> Aggregator_2
    -> SurfaceNormalCalculator
    -> inputWalls_-__NeighborFinder_CANDIDATE
inputWalls_-__NeighborFinder_CANDIDATE: Junction
    -> NeighborFinder [CANDIDATE]
    -> FeatureMerger [SUPPLIER]
PythonCaller_mainWallFinder
    PYTHONSYMBOL = FeatureProcessor
    PYTHONSOURCE:
      import fme
      import fmeobjects
      import math


      # Template Class Interface:
      # When using this class, make sure its name is set as the value of
      # the 'Class or Function to Process Features' transformer parameter
      class FeatureProcessor(object):
          def __init__(self):
              self.lineDict = {} # For nodes (intersection points)
              self.centrePoint = None

          def input(self,feature): # This function is called every time a feature is added
              if feature.getAttribute('buildingCentre'):
                  f = feature.getGeometry()
                  self.centrePoint = f.getXYZ()
              elif feature.getAttribute('wallOrderID')  >=0 :
                  if feature.getAttribute('wallOrderID') in self.lineDict.keys():
                      self.lineDict[feature.getAttribute('wallOrderID')].append(feature)
                  else:
                      self.lineDict[feature.getAttribute('wallOrderID')] = [feature]


          def close(self):
              # To find line segments starting at the building's walls
              closeLine = [] # Saving all line segment touchg walls. Not really needed
              mainWall = (999999, -1) # Saving closest wall only
              for key in self.lineDict:
                  tempMin = 999999
                  featureList = self.lineDict[key]
                  for lineSeg in featureList:
                      geo = lineSeg.getGeometry()
                      pointList = geo.getPoints()
                      for p in pointList:
                          tempXYZ = p.getXYZ()
                          tempDist = math.sqrt((self.centrePoint[0]-tempXYZ[0])**2 + (self.centrePoint[1]-tempXYZ[1])**2)
                          if tempDist < tempMin:
                              tempMin = tempDist
                              tempFea = lineSeg
                              tempLen = lineSeg.getAttribute('_length')

                  if tempLen < mainWall[0]:
                      mainWall = (tempLen, lineSeg.getAttribute('wallOrderID'), tempFea)
                      mainWallKey = key # To acces the shorest intersection line later

                  closeLine.append((tempFea,tempLen))

                  print closeLine
                  print mainWall
              mainWallFeature = mainWall[2]
              newFeature = fmeobjects.FMEFeature()
              newFeature.setGeometry(mainWallFeature.getGeometry())
              newFeature.setAttribute('closeNode', True)
              self.pyoutput(newFeature)
    NEW_ATTRIBUTES = closeNode
    -> NeighborFinder [BASE]
NeighborFinder
    MODE = Bases and Candidates
    MEASURES_FROM_CANDIDATE = Yes
    INSERT_VERTEX = No
    MEASURE_TYPE = Continuous
    TREAT_POLYGON_AS = Lines
    K = 1
    CANDIDATES_FIRST = No
    ATTR_ACCUM_MODE = Only Use Candidate
    MATCHED -> FeatureMerger [REQUESTOR]
FeatureMerger
    REJECT_NULL_MISSING_KEYS = No
    PROCESS_DUPS = No
    ATTR_CONFLICT_RES = Use Requestor
    MERGE_TYPE = Attributes and Geometry
    JOIN_KEYS = @Value(wallOrderID) @Value(wallOrderID) AUTO
    SUPPLIERS_FIRST = No
    IGNORE_NULLS = No
    ATTR_ACCUM_MODE = Merge Supplier
    MERGED -> mainWallFinder_Output (output)
mainWallFinder_Output (output)

Bookmark: Finding intersections points between roads and surface normals of the walls.
Note: The features to find the shortest distance from. / In this case roads and biking paths.
Intersector_Input (input)
    -> Intersector
Note: Saving normal from wall instead since there a / re problem with normals for donuts.
SurfaceNormalCalculator
    Ok -> CenterPointReplacer_walls
CenterPointReplacer_walls
    MODE = Center Point
    POINT -> Extruder_2
Note: Extruding from centre point in / surface normal direction.
Extruder_2
    EXTRUSION_Y = @Value(normalY)
    EXTRUSION_X = @Value(normalX)
    DISTANCE = 1000
    EXTRUSION_Z = 0.0
    DIRECTION = Specified
    EXTRUDED -> Intersector
Intersector
    SEG_ATTR = _segments
    SEPARATE_COLLINEAR_SEGMENTS = No
    DUPLICATE_Z_NODES = No
    GENERATE_LIST_DROP = NO
    OV_ATTR = _overlaps
    MEASURE_TYPE = Continuous
    ATTRS_ACCUM_MODE = Use Attributes From One Feature
    PERFORM_SELF_INTERSECTION = No
    DEAGGREGATE_INPUT = Yes
    INTERSECTED -> LengthCalculator

Bookmark: To get centre of building
Aggregator_2
    ORDERED = No
    MODE = Geometry - Assemble One Level
    ID_SELECTION = ID and Parent ID
    ACCUM_ATTRS_NAME = Use Attributes From One Feature
    SEP = ,
    AGGREGATE_TYPE = Homogeneous Collection (If Possible)
    PRESERVE_ID = No
    ATTR_TO_TRAIT = Yes
    AGGREGATE -> CenterPointReplacer_building
CenterPointReplacer_building
    MODE = Center Point
    POINT -> AttributeCreator_3
AttributeCreator_3
    ATTR_TABLE = SET_TO buildingCentre = 1
    -> PythonCaller_mainWallFinder

Bookmark: Getting length of intersection lines
LengthCalculator
    LEN_ATTR = _length
    DIM = 2
    MULT = 1
    -> Sorter_2
Sorter_2
    SORT_PARM = _length NUMERIC ASCENDING
    SORTED -> Counter_IntersectionLines
Counter_IntersectionLines
    SCOPE = Local
    CNT_ATTR = _countIntersectionLines
    DOMAIN = counter
    START = 0
    -> AttributeKeeper_3
AttributeKeeper_3
    KEEP_ATTRS = _countIntersectionLines,wallOrderID,_length
    -> PythonCaller_mainWallFinder

FME custom transformer MinZ

Input (input)
    -> AttributeCreator
AttributeCreator
    ATTR_TABLE = SET_TO _zminval
    -> BoundsExtractor
BoundsExtractor
    YMIN = _ymin
    ZMIN = _zmin
    YMAX = _ymax
    ZMAX = _zmax
    XMIN = _xmin
    XMAX = _xmax
    -> PythonCaller
PythonCaller
    PYTHONSYMBOL = FeatureProcessor
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    -> Output (output)
Output (output)

FME custom transformer IFC2CityGML_GetGrandParentId

Parameters:
- ATTR_TO_ENCODE =   # " " Attribute to Encode
- DEST_ATTR = gml_parent_id   # TYPE:varchar(200) Destination Attribute

BinaryEncoder_Input (input)
    -> BinaryEncoder
BinaryEncoder
    ATTR_TO_ENCODE = $(ATTR_TO_ENCODE)
    DEST_ATTR = _parent_id
    ENCODING_TYPE = HEX
    -> VariableRetriever
VariableRetriever
    SCOPE = Global
    VARNAME = p@Value(_parent_id)
    VALUE_ATTR = _gparent_id
    -> BinaryDecoder
BinaryDecoder
    ATTR_ENCODING = utf-8
    DEST_ATTR = $(DEST_ATTR)
    ENCODING_TYPE = HEX
    ATTR_TO_DECODE = _gparent_id
    -> Output (output)
Output (output)

FME custom transformer PointCloudClipper

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    EXTRACT_RASTER_NODATA_NAME = No
    SPACING = 20
    GROUP_BY = ifc_unique_id
    ATTRS_TO_PRESERVE = ifc_parent_unique_id,String
    ACCUM_ATTRS_NAME = Yes
    -> Clipper_2 [CLIPPEE]
Clipper (input)
    -> Clipper_2 [CLIPPER]
Clipper_2
    BOUNDARY_CASES = Treat as Inside
    LINES_AS_SEGMENTS = No
    CLIPPED_ATTR = _clipped
    MISSING_VAL_MODE = Compute
    MEASURE_TYPE = Continuous
    CLIP_TYPE = Single Clipper
    PRESERVE_CLIPPEE_EXTENTS = No
    VAL_SOURCE = Clippee Only
    CREATE_AGGREGATES = Yes
    INSIDE -> PointCloudCoercer
    INSIDE -> Output_3D (output)
PointCloudCoercer
    POINT_COMPONENTS_PRESERVE_DISPLAY = Attributes
    PART_NUMBER_ATTR_NAME = _part_number
    ACCUM_ATTRS_NAME = Yes
    CONVERT_TO_DISPLAY = Individual Points
    COERCED -> 2DForcer
2DForcer
    2D -> HullAccumulator
HullAccumulator
    GROUP_BY = ifc_unique_id
    HULLTYPE_PARAM = Convex ()
    3DMODE_PARAM = 2D
    HULL -> Output_2D (output)
Output_2D (output)
Output_3D (output)

FME custom transformer Ifc2surfacesParts

Parameters:
- IFC_UNIQUE_ID = @Value(ifc_unique_id)   # Ifc Unique Id
- IFC_PARENT_UNIQUE_ID = @Value(ifc_parent_unique_id)   # Ifc Parent Unique Id
- GML_PARENT_ID = @Value(gml_parent_id)   # Gml Parent Id
- _VZ = @Value(_vz)   # Vz

IntersectionLineCreatetor_SurfaceFootprintReplacer_Input_1 (input)
    -> IntersectionLineCreatetor [SurfaceFootprintReplacer_Input]
Note: Creating intersection line based / on footprint of slab
IntersectionLineCreatetor
    2DForcer_2_2D -> OuterWallSegmentFinder [Intersector_line_walls_Input]
NormalVectorFinder_Roof_CoordinateExtractor_Input (input)
    -> TestFilter
TestFilter
    DEFAULT_VALUE = <UNFILTERED>
    TEST_LIST = BOOL_OP,OR,COMPOSITE_TEST,<Unused>,TEST_CLAUSE,"TEST @Value(_vz) > 0",upLooking
    upLooking -> AreaCalculator
Note: SlopeCalculator
Junction_2
    -> Junction_4
BinaryEncoder_Door_Input (input)
    -> BinaryEncoder_Door
BinaryEncoder_Door
    ATTR_TO_ENCODE = ifc_parent_unique_id
    DEST_ATTR = _parent_id
    ENCODING_TYPE = HEX
    -> VariableRetriever_Door
VariableRetriever_Door
    SCOPE = Global
    VARNAME = t@Value(_parent_id)
    VALUE_ATTR = _parent_type
    -> AttributeRenamer_Door
AttributeRenamer_Door
    ATTR_TABLE:
      RENAME_SET_DEFAULT ifc_parent_unique_id > gml_parent_id
      RENAME_SET_DEFAULT ifc_unique_id > gml_id
    -> Tester_Door
Tester_Door
    TEST_CLAUSE = TEST @Value(_parent_type) NOT_= IfcCurtainWall
    BOOL_OP = OR
    TEST_MODE = Automatic
    PASSED -> IFC2CityGML_GetGrandParentId_Door [BinaryEncoder_Input]
    FAILED -> CityGMLGeometrySetter_Door
IFC2CityGML_GetGrandParentId_Door
    ATTR_TO_ENCODE = gml_parent_id
    DEST_ATTR = gml_parent_id
    -> CityGMLGeometrySetter_Door
CityGMLGeometrySetter_Door
    GEOM = lod3MultiSurface
    ROLE = opening
    -> AttributeKeeper_2
Note: Temporary to keep number af attributes down
AttributeKeeper_2
    KEEP_ATTRS = _gparent_id,Tag,ifc_parent_id,_geometry_name,_parent_id,_parent_type,gml_id
    -> Junction
    -> Junction_5
Note: FeatureMerger_Doors_Walls_Merged : Input
Junction
Note: FeatureMerger_Doors : Requestor
Junction_5
NormalVectorFinder_Walls_CoordinateExtractor_Input (input)
    -> TestFilter_Wall_Normal
TestFilter_Wall_Normal
    DEFAULT_VALUE = <UNFILTERED>
    TEST_LIST = BOOL_OP,OR,COMPOSITE_TEST,<Unused>,TEST_CLAUSE,"TEST @Value(_vz) = 0",Vertical
    Vertical -> AttributeRenamer_3
AttributeRenamer_3
    ATTR_TABLE:
      RENAME_SET_DEFAULT _vx > _vx_wall
      RENAME_SET_DEFAULT _vy > _vy_wall
      RENAME_SET_DEFAULT _vz > _vz_wall
    -> Sorter_2
Sorter_2
    SORT_PARM = ifc_unique_id NUMERIC ASCENDING
    SORTED -> Counter_2
Counter_2
    SCOPE = Local
    CNT_ATTR = _uuid
    DOMAIN = counter
    START = 0
    -> TestFilter_Walls
    -> FeatureMerger_3 [SUPPLIER]
Note: Filtering walls by building storey.
TestFilter_Walls
    DEFAULT_VALUE = <UNFILTERED>
    TEST_LIST = BOOL_OP,OR,COMPOSITE_TEST,<Unused>,TEST_CLAUSE,"TEST @Value(ifc_parent_unique_id) = 3L6rYPtbn4bvG0fUNlvutn_124",Main_building,BOOL_OP,OR,COMPOSITE_TEST,<Unused>,TEST_CLAUSE,"TEST @Value(ifc_parent_unique_id) = 3L6rYPtbn4bvG0fUNlumJV_136",Dormer
    Main_building -> AttributeRemover_2
    Dormer -> Counter_DormerID
Note: SurfaceNormalCalculator_2 : INPUT
Junction_12
AttributeRemover_2
    REMOVE_ATTRS = _vx0,_vx1,_y0,_vz0,_z0,_z2,_vz1,_vy0,_x2,_y2,_z1,_x1,_y1,_vy1,_x0
    -> WallsTo2D_Python [SurfaceFootprintReplacer_3_Input]
Note: Creating 2D lines of wall surfaces
WallsTo2D_Python
    CoordinateExtractor_End_Wall_Output -> LineDirectionChanger [AttributeCreator_2_Input]
    CoordinateExtractor_End_Wall_Output -> OuterWallSegmentFinder [Intersector_line_walls_Input]
Note: We need all lines to be in clockwise / direction.
LineDirectionChanger
    _X_END_WALL = @Value(_x_end_wall)
    _VY = @Value(_vy_wall)
    _Y_END_WALL = @Value(_y_end_wall)
    _Y_START_WALL = @Value(_y_start_wall)
    _X_START_WALL = @Value(_x_start_wall)
    _VX = @Value(_vx_wall)
    AttributeRemover_3_Output -> AttributeKeeper_4
    AttributeRemover_3_Output -> OuterWallSegmentFinder [FeatureMerger_Supplier]
OuterWallSegmentFinder
    INTERSECTLINE = @Value(IntersectLine)
    _UUID = @Value(_uuid)
    FeatureMerger_Merged -> AttributeKeeper_Input_Python
AttributeKeeper_Input_Python
    KEEP_ATTRS = _uuid
    -> AttributeCreator_6
AttributeCreator_6
    ATTR_TABLE = SET_TO outerWall = 1
    -> FeatureMerger_2 [SUPPLIER]
AttributeKeeper_4
    KEEP_ATTRS = _start_x,_uuid,_start_y,_end_x,_end_y
    -> FeatureMerger_2 [REQUESTOR]
FeatureMerger_2
    REJECT_NULL_MISSING_KEYS = No
    PROCESS_DUPS = No
    ATTR_CONFLICT_RES = Use Requestor
    MERGE_TYPE = Attributes and Geometry
    JOIN_KEYS = @Value(_uuid) @Value(_uuid) AUTO
    SUPPLIERS_FIRST = No
    IGNORE_NULLS = No
    ATTR_ACCUM_MODE = Merge Supplier
    MERGED -> PythonCaller_wallFinder
    UNMERGED_REQUESTOR -> AttributeCreator_7
AttributeCreator_7
    ATTR_TABLE = SET_TO outerWall = 0
    -> PythonCaller_wallFinder
PythonCaller_wallFinder
    PYTHONSYMBOL = FeatureProcessor
    PYTHONSOURCE:
      import fme
      import fmeobjects
      import math
      # Template Function interface:
      # When using this function, make sure its name is set as the value of
      # the 'Class or Function to Process Features' transformer parameter
      def OuterWallFinder(feature):
          pass

      class Point:
          def __init__(self, x, y):
              self.x = float(x)
              self.y = float(y)

          def dist(self, other):
              return math.sqrt((self.x-other.x)**2 + (self.y-other.y)**2)

          def __str__(self):
              return 'Point({},{})'.format(self.x,self.y)

      def owFinder(fl): # Added to run from FME

          wallOrder = 0 # Keeping track of the order of the wall segment
          eps = 10 # Deviation in mm when comparing start -> end
          epsCoords = 10 # Deviation when finding candidate points (seems same value
          # can be used for both)

          # Dictionary when the unique wall surface id is the key and the start and end
          # of the wall segment are saved as Point objects
          lineDict = dict()

          # Adding all wall segments to the dictionary
          for row in fl:
              uuid = row.getAttribute('_uuid')
              x1 = row.getAttribute('_start_x')
              x2 = row.getAttribute('_end_x')
              y1 = row.getAttribute('_start_y')
              y2 = row.getAttribute('_end_y')
              ow = row.getAttribute('outerWall')
              lineDict[uuid] = [Point(x1, y1), Point(x2, y2)]
              if ow:
                  owStart = uuid

          # For saving uuid of the wall segments. After this script is run this will
          # list all the outer wall segments
          owList = [(wallOrder, owStart)]
          startPoint = lineDict[owStart][0] # Need to keep the start point to know when last wall is found

          tempStartPoint = lineDict[owStart][0]
          tempEndPoint = lineDict[owStart][1]
          tempow = owStart # Current outer wall segment

          # This loop will run until the last outer wall is found
          while startPoint.dist(tempEndPoint) > eps:

              # finding candidate walls (connected to current wall segment)
              tempCandidates = []
              for uuid, points in lineDict.iteritems():
                  if tempEndPoint.dist(points[0]) < epsCoords:
                      tempCandidates.append(uuid)

              # Reversing current outer wall to find angles. The wall segment needs to
              # be reversed to get vectors that start at the same point, both for the
              # current wall and the candidates tested
              tempStartPoint = lineDict[tempow][1]
              tempEndPoint = lineDict[tempow][0]

              #####################################################
              # Getting angle between vectors with the dot product
              #####################################################

              # Vectors and lenght of current outer wall segment
              vx1 = tempEndPoint.x - tempStartPoint.x
              vy1 = tempEndPoint.y - tempStartPoint.y
              vx1len = tempStartPoint.dist(tempEndPoint)

              #For saving candidate wall segments as vectors.
              # index 0 = uuid
              # index 1 = tuple with x- and y-vector following candidate wall segment
              # index 2 = lenght of wall segment
              # index 3 = Clockwise angle from current wall segment
              # index 4 = True is vector is point to the right from the current wall segment
              # (looking from end -> start). From cross product.
              candidateVectors = []

              # Looping over all candidate wall segments
              for uuid in tempCandidates:
                  # End points of current wall segment
                  ts = lineDict[uuid][0]
                  te = lineDict[uuid][1]

                  # Vectors and lenght of current candidate wall segment
                  vx2 = te.x - ts.x
                  vy2 = te.y - ts.y
                  vx2len = ts.dist(te)

                  # Temporary solution since some input walls are polygons instead of lines. These have start = end and
                  # hence results in vectors with length = 0. This needs to be handled in FME.
                  # In the KTH model all outer walls are "correct" only some candidates are handled here
                  if vx2len*vx1len == 0:
                      wallSegmentAngle = 180
                      wallSegmentSide = 0
                  else:
                      # Angle
                      # NB!!!! round required below since there we special cases when math.acos was called with
                      # arguments like -1.000000000x resulting in math domain error
                      wallSegmentAngle = math.acos(round(((vx1 * vx2) + (vy1 * vy2)) / (vx1len * vx2len),4))*180/math.pi;
                      # Side true if to the right
                      wallSegmentSide = (vx1 * (te.y - tempStartPoint.y)) - (vy1 * (te.x - tempStartPoint.x)) < 0;
                  # Finding clockwise angle
                  if wallSegmentSide:
                      wallAngleCW = wallSegmentAngle
                  else:
                      wallAngleCW = 360 - wallSegmentAngle

                  candidateVectors.append((uuid,(vx2,vy2),vx2len,wallAngleCW,wallSegmentSide))

              minAngle = 360 # Starting with high to get the smallest angle
              tempUUID = ''

              for tempCandidate in candidateVectors:
                  if tempCandidate[3] < minAngle:
                      tempUUID = tempCandidate[0]
                      minAngle = tempCandidate[3]


              # Adding the found wall segment to the list and updating
              wallOrder += 1
              owList.append((wallOrder, tempUUID))
              tempStartPoint = lineDict[tempUUID][0]
              tempEndPoint = lineDict[tempUUID][1]
              tempow = tempUUID # Current outer wall segment

          return owList


      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):




              print '*'*32
              print self.featureList
              print '*'*32







              owFound = owFinder(self.featureList)

              for feature in self.featureList:
                  temp_uuid = feature.getAttribute('_uuid')
                  for wo, tu in owFound: # ow = wall order, tu = uuid
                      if not feature.getAttribute('owOrder') and tu == temp_uuid:
                          feature.setAttribute("owOrder", wo)

                  self.pyoutput(feature)
    NEW_ATTRIBUTES = owOrder
    -> TestFilter_Final_outer_wall
TestFilter_Final_outer_wall
    DEFAULT_VALUE = <UNFILTERED>
    TEST_LIST = BOOL_OP,OR,COMPOSITE_TEST,<Unused>,TEST_CLAUSE,"TEST @Value(owOrder) >= 0",outerWall
    outerWall -> FeatureMerger_3 [REQUESTOR]
Note: Merging wall surfaces with the / 2D outer wall segments to get / 3D geometry.
FeatureMerger_3
    REJECT_NULL_MISSING_KEYS = No
    PROCESS_DUPS = No
    ATTR_CONFLICT_RES = Use Requestor
    MERGE_TYPE = Attributes and Geometry
    JOIN_KEYS = @Value(_uuid) @Value(_uuid) AUTO
    SUPPLIERS_FIRST = No
    IGNORE_NULLS = No
    ATTR_ACCUM_MODE = Merge Supplier
    MERGED -> SurfaceSplitter
Note: Removing back of 2-sided wall surfaces
SurfaceSplitter
    FRONT -> PythonCaller_WallRoofAdjuster
AttributeKeeper
    KEEP_ATTRS = wallOrderID,donut
    -> Tester_Donut_walls
    -> Tester
Junction_10
    -> AttributeCreator_mainWalls
NormalVectorFinder_2_CoordinateExtractor_Input (input)
    -> AttributeRenamer
Note: Temporary solution to rename normal vectors of windows
AttributeRenamer
    ATTR_TABLE:
      RENAME_SET_DEFAULT _vx > _vx_window
      RENAME_SET_DEFAULT _vy > _vy_window
      RENAME_SET_DEFAULT _vz > _vz_window
    -> AttributeRemover
AttributeRemover
    REMOVE_ATTRS = _vy0,_vz1,_x0,_y0,_z1,_vz0,_y2,_vy1,_x1,_x2,_y1,_z0,_z2,_vx0,_vx1
    -> AttributeRenamer_Window
AttributeRenamer_Window
    ATTR_TABLE = RENAME_SET_DEFAULT ifc_unique_id > gml_id
    -> IFC2CityGML_GetGrandParentId_Window [BinaryEncoder_Input]
IFC2CityGML_GetGrandParentId_Window
    ATTR_TO_ENCODE = ifc_parent_unique_id
    DEST_ATTR = gml_parent_id
    -> CityGMLGeometrySetter_Window
CityGMLGeometrySetter_Window
    GEOM = lod3MultiSurface
    ROLE = opening
    -> AttributeKeeper_3
Note: Temporary to keep number af attributes down
AttributeKeeper_3
    KEEP_ATTRS = _gparent_id,Tag,_vz_window,Name,_geometry_name,_vx_window,_parent_id,ifc_parent_unique_id,gml_id,_vy_window
    -> UUIDGenerator_2
Note: To get unique ID for all parts
UUIDGenerator_2
    UUID_ATTR = _uuid_window
    -> Junction_3
Note: FeatureMerger_Windows : Requestor
Junction_3

Bookmark: To split into main roof and dormer
AreaCalculator
    AREA_ATTR = _areaRoof
    AREA_TYPE = Plane Area
    MULT = 1
    -> Sorter
Sorter
    SORT_PARM = _areaRoof NUMERIC DESCENDING
    SORTED -> Counter
Counter
    SCOPE = Local
    CNT_ATTR = _countRoofArea
    DOMAIN = counterRoofArea
    START = 0
    -> TestFilter_4
TestFilter_4
    DEFAULT_VALUE = <UNFILTERED>
    TEST_LIST = BOOL_OP,OR,COMPOSITE_TEST,<Unused>,TEST_CLAUSE,"TEST @Value(_countRoofArea) <= 1",mainRoof,BOOL_OP,OR,COMPOSITE_TEST,<Unused>,TEST_CLAUSE,"TEST @Value(_countRoofArea) >= 2",dormer
    mainRoof -> CoordinateExtractor_MainRoof
    mainRoof -> FeatureMerge_mainRoofTriangles [SUPPLIER]
    mainRoof -> FeatureColorSetter_mainRoof
    dormer -> CoordinateExtractor_Dormer
    dormer -> FeatureMerge_dormerTriangles [SUPPLIER]
    dormer -> FeatureColorSetter_dormerRoof

Bookmark: Dormers - Note that the part of this is hard coded.
CoordinateExtractor_Dormer
    MODE = All Coordinates
    LIST_NAME = _indices
    -> PythonCaller_TriangleSplitter_Dormer
PythonCaller_TriangleSplitter_Dormer
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.id = 100 #Starting with ID = 100 for dormers

          def input(self,feature):
              #self.featureList.append(feature)
              #Getting the list of coordinates
              xlist = feature.getAttribute('_indices{}.x')
              ylist = feature.getAttribute('_indices{}.y')
              zlist = feature.getAttribute('_indices{}.z')
              xlist = map(float, xlist)
              ylist = map(float,ylist)
              zlist = map(float, zlist)

              count = feature.getAttribute('_countRoofArea') # Need to add this attribute to merge with roofs later

              # Creating two triangles
              # NB!!!! "Extra" coordinates are created except first and last, hence, the indices below.
              line1Points = [(xlist[0], ylist[0], zlist[0]), (xlist[1], ylist[1], zlist[1]), (xlist[3], ylist[3], zlist[3])]
              line2Points = [(xlist[3], ylist[3], zlist[3]), (xlist[5], ylist[5], zlist[5]), (xlist[7], ylist[7], zlist[7])]
              line1 = fmeobjects.FMELine(line1Points)
              line2 = fmeobjects.FMELine(line2Points)
              poly1 = fmeobjects.FMEPolygon(line1)
              poly2 = fmeobjects.FMEPolygon(line2)

              newFeature1 = fmeobjects.FMEFeature()
              newFeature1.setGeometry(poly1)
              newFeature1.setAttribute('triID', self.id)
              newFeature1.setAttribute('count', count)
              newFeature1.setAttribute('triangle', True)
              self.pyoutput(newFeature1)

              newFeature2 = fmeobjects.FMEFeature()
              newFeature2.setGeometry(poly2)
              newFeature2.setAttribute('triID', self.id+1)
              newFeature2.setAttribute('count', count)
              newFeature2.setAttribute('triangle', True)
              self.pyoutput(newFeature2)

              self.id += 2


          def close(self):
              pass
    NEW_ATTRIBUTES = triID count triangle
    -> FeatureMerge_dormerTriangles [REQUESTOR]
FeatureMerge_dormerTriangles: FeatureMerger
    REJECT_NULL_MISSING_KEYS = No
    PROCESS_DUPS = No
    ATTR_CONFLICT_RES = Use Requestor
    MERGE_TYPE = Attributes Only
    JOIN_KEYS = @Value(count) @Value(_countRoofArea) AUTO
    SUPPLIERS_FIRST = No
    IGNORE_NULLS = No
    ATTR_ACCUM_MODE = Merge Supplier
    MERGED -> AttributeKeeper_RoofTriangles_2
AttributeKeeper_RoofTriangles_2
    KEEP_LIST = _indices{} ifc_property_set{} ifc_quantity_set{}
    KEEP_ATTRS = ifc_unique_id,triangle,ifc_parent_id,Description,ShapeType,ifc_parent_unique_id,ObjectType,Name,triID,GlobalId,Tag
    -> CoordinateExtractor_2
CoordinateExtractor_2
    MODE = All Coordinates
    LIST_NAME = _indices
    -> PythonCaller_WallDormerAdjuster
Counter_DormerID
    SCOPE = Local
    CNT_ATTR = _dormerID
    DOMAIN = counter
    START = 100
    -> CoordinateExtractor_3
CoordinateExtractor_3
    MODE = All Coordinates
    LIST_NAME = _coords
    -> ListRangeExtractor
ListRangeExtractor
    MAX = _maxZ
    MIN = _minZ
    SRC_LIST = _coords{}.z
    -> AttributeKeeper_5
AttributeKeeper_5
    KEEP_LIST = ifc_property_set{} ifc_quantity_set{}
    KEEP_ATTRS = Description,ifc_unique_id,Tag,ifc_parent_id,_minZ,Axis,Box,_geometry_name,_maxZ,Name,GlobalId,Body,FootPrint,_dormerID,ifc_parent_unique_id,_uuid,ObjectType
    -> TestFilter_2
TestFilter_2
    DEFAULT_VALUE = <UNFILTERED>
    TEST_LIST:
      BOOL_OP,OR,COMPOSITE_TEST,<Unused>,TEST_CLAUSE,"TEST @Value(_uuid) = 33",dormerFront,BOOL_OP,OR,COMPOSITE_TEST,<Unused>,TEST_CLAUSE,"TEST @Value(_uuid) = 29
      TEST @Value(_uuid) = 42",dormerSide
    dormerFront -> AttributeCreator
    dormerSide -> AttributeCreator_2
AttributeCreator
    ATTR_TABLE = SET_TO dormer = front
    -> PythonCaller_WallDormerAdjuster
AttributeCreator_2
    ATTR_TABLE = SET_TO dormer = side
    -> PythonCaller_WallDormerAdjuster
PythonCaller_WallDormerAdjuster
    PYTHONSYMBOL = FeatureProcessor
    PYTHONSOURCE:
      import fme
      import fmeobjects
      import math
      import numpy

      # Finds in which triangle the point p is located
      # Strictly speadking findest the closest corner point
      # since we know that the point is inside one of the triangles.
      # roofTriangle = the roof triangles in self.roofList
      # p = (x,y,z) tuple with the coordinates of the point
      def triangleFinder(roofTriangle,p):
          shortDist = 99999999
          triID = -1 # Which roof triangel the point is inside
          for triKey in roofTriangle:
              tri = roofTriangle[triKey]
              if not triKey == tri.getAttribute('triID'):
                  break # Something wrong with indices
              triGeo = tri.getGeometry()
              triPoly = triGeo.getBoundaryAsCurve()
              triPoints = triPoly.getPoints()

              for tempPoint in triPoints:
                  xyz = tempPoint.getXYZ()
                  tempDist = math.sqrt((xyz[0]-p[0])**2 + (xyz[1]-p[1])**2)
                  if tempDist < shortDist:
                      shortDist = tempDist
                      triID = triKey

          return triID


      # Calculating the offset of the z-coordinate
      # tri = current triangle
      # point = current point
      def zOffset(tri, point):
          # To get (x,y,z) tuples from the triangle
          triGeo = tri.getGeometry()
          triPoly = triGeo.getBoundaryAsCurve()
          triPoints = triPoly.getPoints()
          triPoints = triPoints[:3] # Last point is same as first point

          triXYZ = [x.getXYZ() for x in triPoints]

          b = numpy.array([[point[0]],[point[1]],[1]])
          A = numpy.array([[triXYZ[0][0], triXYZ[1][0], triXYZ[2][0]],[triXYZ[0][1], triXYZ[1][1], triXYZ[2][1]],[1,1,1]])
          coeff = numpy.linalg.solve(A, b)

          alfa = coeff[0]
          beta = coeff[1]
          gamma = coeff[2]

          zPoint = triXYZ[0][2] * alfa + triXYZ[1][2] * beta + triXYZ[2][2] * gamma

          return zPoint


      # Template Class Interface:
      # When using this class, make sure its name is set as the value of
      # the 'Class or Function to Process Features' transformer parameter
      class FeatureProcessor(object):
          def __init__(self):
              self.wallDict = {}
              self.roofDict = {}
              self.sideList = []

          def input(self,feature): # This function is called every time a feature is added

              if feature.getAttribute('triangle'):
                  self.roofDict[feature.getAttribute('triID')] = feature
              else:
                  self.wallDict[feature.getAttribute('_dormerID')] = feature
                  # The lines below gives the x,y coordinates of the side walls of the dormer.
                  # The front side of the dormer needs to be extended to these coordinates.
                  if feature.getAttribute('dormer') == 'side':
                      minZ = float(feature.getAttribute('_minZ'))
                      s = feature.getGeometry()
                      s = s.getAsArea()
                      s = s.getBoundaryAsCurve()
                      s = s.getPoints()
                      for p in s:
                          xyz = p.getXYZ()
                          if xyz[2] - minZ < 10:
                              self.sideList.append(xyz)



          def close(self):

              # Iterating over all walls to "lift" the higher coords to touch the roof
              for wallKey in self.wallDict:
                  wall = self.wallDict[wallKey]
                  wallDonut = False # To check if a geometry is donut
                  wallPolygon = False
                  wallFace = wall.getGeometry() # We get the geometry as a face
                  wallGeo = wallFace.getAsArea() # We need the "original" geometry

                  # Have not found a way of checking what geomatry type the area is
                  # so using try to see if it is donut och polygon
                  try:
                      # Only outer boundary is interesting (i.e. openings not relevant)
                      wallDonut = wallGeo.getOuterBoundaryAsCurve()
                      pointList = wallDonut.getPoints()
                  except:
                      wallPolygon = wallGeo.getBoundaryAsCurve()
                      pointList = wallPolygon.getPoints()

                  # Handling both donuts and polygons in the same fashion
                  for tempPoint in xrange(len(pointList)):
                      tempXYZ = pointList[tempPoint].getXYZ()
                      if tempXYZ[2] > 0: # No need to check ground level points

                          ###########################################################
                          # Extending the front wall of the dormer
                          # Ugly solution now..............................

                          # If front wall and coordinate is lower (minimum z).
                          #if wall.getAttribute('dormer') == 'front' and (tempXYZ[2] - float(wall.getAttribute('_minZ')) < 10):

                          # Need to move also upper point (vertical above lower outer corners of the dormer) since it is the upper
                          # point that is offset to touch the roof.
                          if wall.getAttribute('dormer') == 'front':

                              if math.sqrt((tempXYZ[0] - self.sideList[0][0])**2 + (tempXYZ[1] - self.sideList[0][1])**2) < 1000:

                                  # Updates tempXYZ since used later for finding correct triangle
                                  tempXYZ = (self.sideList[0][0], self.sideList[0][1], tempXYZ[2])

                                  print tempXYZ

                                  # Updates pointList since used for adjusting boundary later
                                  pointList[tempPoint].setX(self.sideList[0][0])
                                  pointList[tempPoint].setY(self.sideList[0][1])

                              elif math.sqrt((tempXYZ[0] - self.sideList[1][0])**2 + (tempXYZ[1] - self.sideList[1][1])**2) < 500:

                                  # Updates tempXYZ since used later for finding correct triangle
                                  tempXYZ = (self.sideList[1][0], self.sideList[1][1], tempXYZ[2])

                                  # Updates pointList since used for adjusting boundary later
                                  pointList[tempPoint].setX(self.sideList[1][0])
                                  pointList[tempPoint].setY(self.sideList[1][1])


                          # Finding which roof triangle the point is inside
                          rt = triangleFinder(self.roofDict, tempXYZ)

                          # And finding the new z-value
                          zOff = zOffset(self.roofDict[rt], tempXYZ)
                          zOff = zOff[0]

                          ###########################################################
                          # Need to check if first"last point is adjusted
                          ###########################################################

                          # To avoid adjusting z-vales that are e.g. higher part of door (since these are above ground)
                          ###########################################################
                          # Need to check roof thickness instead of hard coding
                          ###########################################################
                          # Front treated separately since sides also needs y-offset
                          if wall.getAttribute('dormer') == 'front' and zOff - tempXYZ[2] < 1000:
                              pointList[tempPoint].setX(tempXYZ[0])
                              pointList[tempPoint].setY(tempXYZ[1])
                              pointList[tempPoint].setZ(zOff)

                          # This is a quick and dirty solution that works here since sides are parallell to the x-axis
                          if wall.getAttribute('dormer') == 'side':
                              sideSlope = (4263.0-1855.0)/(6042.0-4919.0) # Hard coded from coordinates


                              if ((zOff - tempXYZ[2]) < 1000) and (tempXYZ[1] > -1860):
                                  pointList[tempPoint].setY(tempXYZ[1] - (tempXYZ[2] - zOff)*sideSlope)
                                  pointList[tempPoint].setZ(zOff)

                              elif ((zOff - tempXYZ[2]) < 1000):
                                  pointList[tempPoint].setZ(zOff)



                  # Creating a new booundary. The bounday line is treated in the
                  # same way for both polygon and donut.
                  newFeature = fmeobjects.FMEFeature()
                  newLine = fmeobjects.FMELine([x.getXYZ() for x in pointList])
                  newFeature.setAttribute('wallOrderID', int(wallKey))
                  newFeature.setAttribute('dormer', wall.getAttribute('dormer'))

                  if wallPolygon:
                      newPoly = fmeobjects.FMEPolygon(newLine)
                      newFeature.setGeometry(newPoly)
                  else:
                      wallGeo.setOuterBoundaryCurve(newLine)
                      newFeature.setGeometry(wallGeo)
                      newFeature.setAttribute('donut', 'True')

                  self.pyoutput(newFeature)
    NEW_ATTRIBUTES = wallOrderID donut
    -> Tester_Donut_dormer

Bookmark: Main roof, no modifications (except appearance)
FeatureColorSetter_mainRoof
    COLOR = 0.666667,0.666667,0
    MODE = Fixed
    FILL_COLOR = 0.666667,0.666667,0
    COLORED -> AttributeCreator_mainRoof

Bookmark: Attributes for element type
  Creating attribute to separate the element types in the building permit test.
AttributeCreator_mainRoof
    ATTR_TABLE = SET_TO type = mainRoof
    -> Offsetter
    -> Junction_2
AttributeCreator_dormerRoof
    ATTR_TABLE = SET_TO type = dormerRoof
    -> Offsetter
AttributeCreator_dormerWindow
    ATTR_TABLE = SET_TO type = dormerWindow
    -> Offsetter
AttributeCreator_dormerWall
    ATTR_TABLE = SET_TO type = dormerWall
    -> Offsetter
    -> Junction_12
    -> Junction_11
Note: TestFilter_5 : Input
Junction_11
    -> Junction_14
AttributeCreator_door
    ATTR_TABLE = SET_TO type = door
    -> Offsetter
AttributeCreator_window
    ATTR_TABLE = SET_TO type = window
    -> Offsetter
Note: PythonCaller_wallFinder_2 : Output
AttributeCreator_mainWalls
    ATTR_TABLE = SET_TO type = mainWalls
    -> Offsetter
    -> Junction_15
Note: TestFilter_5 : Input
Junction_15
    -> Junction_16

Bookmark: Creating 45 degree planes for deriving height of the facades.
  Testing if roof surfaces are steeper than 45 degree. If steeper 45-degree planes are created. If less then 45 degree, the building heigth will be calcualted as the height where the facade touch the roof.
  NB!!!!! Can only handle one roof surface.
Note: AttributeCreator_mainRoof : Output
Junction_4
    -> TestFilter_7
TestFilter_7
    DEFAULT_VALUE = <UNFILTERED>
    TEST_LIST = BOOL_OP,OR,COMPOSITE_TEST,<Unused>,TEST_CLAUSE,"TEST @Value(_countRoofArea) = 0",mainSideRoof
    mainSideRoof -> AttributeKeeper_8
2DForcer_2
    2D -> AreaOnAreaOverlayer [AREA]
PythonCaller_RoofCutter
    PYTHONSYMBOL = FeatureProcessor
    PYTHONSOURCE:
      import fme
      import fmeobjects
      from math import sqrt

      # Reading coordinates from a list of features and returning the coordinates in (x,y,z) tuples.
      def coordinateExtractor(fl):

          xyzList = [] # For keeping the (x,y,z) tuples

          for f in fl:

              geo = f.getGeometry()

              # Have not found a way of checking what geometry type the area is
              # so using try to see if it is donut och polygon and extracting
              # boundary as an FMELine feature
              try:
                  boundaryLine = geo.getOuterBoundaryAsCurve()
              except:
                  boundaryLine = geo.getBoundaryAsCurve()

              p = boundaryLine.getPoints() # List with points

              xyzList.extend([x.getXYZ() for x in p])

          return xyzList


      # Template Class Interface:
      # When using this class, make sure its name is set as the value of
      # the 'Class or Function to Process Features' transformer parameter
      class FeatureProcessor(object):
          def __init__(self):
              self.roofList = []
              self.wallList = []

          def input(self,feature):
              if feature.getAttribute('_countRoofArea') >= 0:
                  self.roofList.append(feature)
              else:
                  self.wallList.append(feature)

          def close(self):

              try:

                  wallCoords = coordinateExtractor(self.wallList)

                  for r in self.roofList:
                      geo = r.getGeometry()
                      cu = geo.getBoundaryAsCurve()
                      pl = cu.getPoints()
                      colist = [tp.getXYZ() for tp in pl]

                      # For all coordinates in current roof (only 4)
                      for ind in xrange(len(colist)):
                          co = colist[ind]
                          for wallCo in wallCoords:

                              # Since the rooftop is not vertically above the highest part of the roof the tolerance
                              # need to be high here and the new coordinate adjsuted also in x and y.
                              if (wallCo[2] > 0) and sqrt((wallCo[0]-co[0])**2 + (wallCo[1]-co[1])**2) < 1000:
                                  colist[ind] = (wallCo[0], wallCo[1], wallCo[2])

                      nl = fmeobjects.FMELine(colist)
                      np = fmeobjects.FMEPolygon(nl)
                      r.setGeometry(np)

                      self.pyoutput(r)

              except:
                  pass
    -> AttributeKeeper_9
AttributeKeeper_9
    KEEP_ATTRS = ifc_unique_id,_countRoofArea,_areaRoof
    -> CoordinateExtractor_6
    -> SlopeCalculator
SlopeCalculator
    -> CoordinateExtractor_8
CoordinateExtractor_8
    MODE = All Coordinates
    LIST_NAME = _indices
    -> ListRangeExtractor_4
ListRangeExtractor_4
    MAX = _max_z
    MIN = _min_z
    SRC_LIST = _indices{}.z
    -> TestFilter_3
TestFilter_3
    DEFAULT_VALUE = <UNFILTERED>
    TEST_LIST = BOOL_OP,OR,COMPOSITE_TEST,<Unused>,TEST_CLAUSE,"TEST @Value(_slope) <= 45",Less or equal to 45
    Less or equal to 45 -> AttributeCreator_low
    <UNFILTERED> -> AttributeCreator_high

Bookmark: Selecting roof to base height calculation on
  Now hard coded via roof area order but needs to connect to the front wall (beräkningsgrundande fasad).
AttributeKeeper_8
    KEEP_ATTRS = ifc_unique_id,_countRoofArea,_areaRoof
    -> 2DForcer_2

Bookmark: Dormer roof, no modifications (except appearance)
FeatureColorSetter_dormerRoof
    COLOR = 0.666667,0.666667,0
    MODE = Fixed
    FILL_COLOR = 0.666667,0.666667,0
    COLORED -> AttributeCreator_dormerRoof

Bookmark: Main roof - creating triangles
  Splitting roof surfaces into triangles for the interpolation to find the z-coordinate where the wall surfaces touches the roof.
CoordinateExtractor_MainRoof
    MODE = All Coordinates
    LIST_NAME = _indices
    -> PythonCaller_TriangleSplitter
PythonCaller_TriangleSplitter
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.id = 0

          def input(self,feature):
              #self.featureList.append(feature)
              #Getting the list of coordinates
              xlist = feature.getAttribute('_indices{}.x')
              ylist = feature.getAttribute('_indices{}.y')
              zlist = feature.getAttribute('_indices{}.z')
              xlist = map(float, xlist)
              ylist = map(float,ylist)
              zlist = map(float, zlist)

              count = feature.getAttribute('_countRoofArea') # Need to add this attribute to merge with roofs later

              # Creating two triangles
              # NB!!!! "Extra" coordinates are created except first and last, hence, the indices below.
              line1Points = [(xlist[0], ylist[0], zlist[0]), (xlist[1], ylist[1], zlist[1]), (xlist[3], ylist[3], zlist[3])]
              line2Points = [(xlist[3], ylist[3], zlist[3]), (xlist[5], ylist[5], zlist[5]), (xlist[7], ylist[7], zlist[7])]
              line1 = fmeobjects.FMELine(line1Points)
              line2 = fmeobjects.FMELine(line2Points)
              poly1 = fmeobjects.FMEPolygon(line1)
              poly2 = fmeobjects.FMEPolygon(line2)

              newFeature1 = fmeobjects.FMEFeature()
              newFeature1.setGeometry(poly1)
              newFeature1.setAttribute('triID', self.id)
              newFeature1.setAttribute('count', count)
              newFeature1.setAttribute('triangle', True)
              self.pyoutput(newFeature1)

              newFeature2 = fmeobjects.FMEFeature()
              newFeature2.setGeometry(poly2)
              newFeature2.setAttribute('triID', self.id+1)
              newFeature2.setAttribute('count', count)
              newFeature2.setAttribute('triangle', True)
              self.pyoutput(newFeature2)

              self.id += 2


          def close(self):
              pass
    NEW_ATTRIBUTES = triID count triangle
    -> FeatureMerge_mainRoofTriangles [REQUESTOR]
Note: Merging with original roof to get attributes back
FeatureMerge_mainRoofTriangles: FeatureMerger
    REJECT_NULL_MISSING_KEYS = No
    PROCESS_DUPS = No
    ATTR_CONFLICT_RES = Use Requestor
    MERGE_TYPE = Attributes Only
    JOIN_KEYS = @Value(count) @Value(_countRoofArea) AUTO
    SUPPLIERS_FIRST = No
    IGNORE_NULLS = No
    ATTR_ACCUM_MODE = Merge Supplier
    MERGED -> AttributeKeeper_RoofTriangles
AttributeKeeper_RoofTriangles
    KEEP_LIST = _indices{} ifc_property_set{} ifc_quantity_set{}
    KEEP_ATTRS = ifc_unique_id,triangle,ifc_parent_id,Description,ShapeType,ifc_parent_unique_id,ObjectType,Name,triID,GlobalId,Tag
    -> CoordinateExtractor
CoordinateExtractor
    MODE = All Coordinates
    LIST_NAME = _indices
    -> PythonCaller_WallRoofAdjuster

Bookmark: Finding windows and keeping walls
  Extracts the windows as holes in donuts and keeps the original walls.
Note: For windows ("up")
Note: For walls ("down")
Tester_Donut_dormer
    TEST_CLAUSE = TEST @Value(donut) = True
    BOOL_OP = OR
    TEST_MODE = Automatic
    PASSED -> DonutHoleExtractor_dormer
    PASSED -> FeatureColorSetter_dormerWalls
    FAILED -> FeatureColorSetter_dormerWalls
DonutHoleExtractor_dormer
    DEAGGREGATE_INPUT = Yes
    HOLE -> FeatureColorSetter_dormerWindows
FeatureColorSetter_dormerWindows
    COLOR = 1,1,0.498039
    MODE = Fixed
    FILL_COLOR = 1,1,0.498039
    COLORED -> AttributeCreator_dormerWindow
FeatureColorSetter_dormerWalls
    COLOR = 0.666667,0.666667,0.498039
    MODE = Fixed
    FILL_COLOR = 0.666667,0.666667,0.498039
    COLORED -> AttributeCreator_dormerWall

Bookmark: Checking if dormer shall be inclued in building height
  Adds the following attributes:
  dormerFraction - The fraction of the wall width covered by a dormer
  dormerTopX  - 
  dormerTopY  -  Coordinates of the top corner of the dormer
  dormerTopZ  -
Note: AttributeCreator_dormerWall : Output
Junction_14
    -> TestFilter_5
Note: AttributeCreator_mainWalls : Output
Junction_16
    -> TestFilter_5
TestFilter_5
    DEFAULT_VALUE = <UNFILTERED>
    TEST_LIST = BOOL_OP,OR,COMPOSITE_TEST,<Unused>,TEST_CLAUSE,"TEST @Value(wallOrderID) = 2",mainWallWithDormer,BOOL_OP,OR,COMPOSITE_TEST,<Unused>,TEST_CLAUSE,"TEST @Value(wallOrderID) = 106",mainWallDormer
    mainWallWithDormer -> AttributeCreator_3
    mainWallDormer -> CoordinateExtractor_7
CoordinateExtractor_7
    MODE = All Coordinates
    LIST_NAME = _indices
    -> AttributeCreator_4
AttributeCreator_4
    ATTR_TABLE = SET_TO isWall = False
    -> 2DForcer_3
2DForcer_3
    2D -> BoundsExtractor_3
BoundsExtractor_3
    YMIN = _ymin
    YMAX = _ymax
    XMIN = _xmin
    XMAX = _xmax
    -> AttributeCreator_5
AttributeCreator_5
    ATTR_TABLE = SET_TO dormerLen = @Evaluate(@sqrt((@Value(_xmax) - @Value(_xmin))**2 + (@Value(_ymax) - @Value(_ymin))**2))
    -> PythonCaller_dormerFraction
AttributeCreator_3
    ATTR_TABLE = SET_TO isWall = True
    -> 2DForcer_4
2DForcer_4
    2D -> BoundsExtractor_4
BoundsExtractor_4
    YMIN = _ymin
    YMAX = _ymax
    XMIN = _xmin
    XMAX = _xmax
    -> AttributeCreator_8
AttributeCreator_8
    ATTR_TABLE = SET_TO wallLen = @Evaluate(@sqrt((@Value(_xmax) - @Value(_xmin))**2 + (@Value(_ymax) - @Value(_ymin))**2))
    -> PythonCaller_dormerFraction
PythonCaller_dormerFraction
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.wall = []
              self.dormer = []

          def input(self,feature):
              if feature.getAttribute('wallLen'):
                  self.wall.append(feature)
              elif feature.getAttribute('dormerLen'):
                  self.dormer.append(feature)


          def close(self):
              # The fraction of the wall len covered by the dormer
              dormerFraction = self.dormer[0].getAttribute('dormerLen')*1.0/self.wall[0].getAttribute('wallLen')

              xl = self.dormer[0].getAttribute('_indices{}.x')
              yl = self.dormer[0].getAttribute('_indices{}.y')
              zl = self.dormer[0].getAttribute('_indices{}.z')

              zm = round(float(max(zl)))

              idx = 0
              while not round(float(zl[idx])) == zm:
                  idx += 1


              self.wall[0].setAttribute('dormerFraction', dormerFraction)
              self.wall[0].setAttribute('dormerTopX', xl[idx])
              self.wall[0].setAttribute('dormerTopY', yl[idx])
              self.wall[0].setAttribute('dormerTopZ', zl[idx])

              self.pyoutput(self.wall[0])
    NEW_ATTRIBUTES = dormerFraction dormerTopX dormerTopY dormerTopZ
    -> PythonCaller_WallRoofAdjuster_2

Bookmark: Connecting walls to roof surface
  "Lifting" the upper edge of the wall surfaces to touch the upper roof surface.
  NB! It only gives correct result when the roof-ridge is vertically above the edge of the wall connected to the roof.
Note: Finding where the wall corners touch / the roof (Z-direction) and adjusting / wall surfaces to touoch the roof.
PythonCaller_WallRoofAdjuster
    PYTHONSYMBOL = FeatureProcessor
    PYTHONSOURCE:
      import fme
      import fmeobjects
      import math
      import numpy

      # Finds in which triangle the point p is located
      # Strictly speadking findest the closest corner point
      # since we know that the point is inside one of the triangles.
      # roofTriangle = the roof triangles in self.roofList
      # p = (x,y,z) tuple with the coordinates of the point
      def triangleFinder(roofTriangle,p):
          shortDist = 99999999
          triID = -1 # Which roof triangel the point is inside
          for triKey in roofTriangle:
              tri = roofTriangle[triKey]
              if not triKey == tri.getAttribute('triID'):
                  break # Something wrong with indices
              triGeo = tri.getGeometry()
              triPoly = triGeo.getBoundaryAsCurve()
              triPoints = triPoly.getPoints()

              for tempPoint in triPoints:
                  xyz = tempPoint.getXYZ()
                  tempDist = math.sqrt((xyz[0]-p[0])**2 + (xyz[1]-p[1])**2)
                  if tempDist < shortDist:
                      shortDist = tempDist
                      triID = triKey

          return triID



      # Calculating the offset of the z-coordinate
      # tri = current triangle
      # point = current point
      def zOffset(tri, point):
          # To get (x,y,z) tuples from the triangle
          triGeo = tri.getGeometry()
          triPoly = triGeo.getBoundaryAsCurve()
          triPoints = triPoly.getPoints()
          triPoints = triPoints[:3] # Last point is same as first point

          triXYZ = [x.getXYZ() for x in triPoints]

          b = numpy.array([[point[0]],[point[1]],[1]])
          A = numpy.array([[triXYZ[0][0], triXYZ[1][0], triXYZ[2][0]],[triXYZ[0][1], triXYZ[1][1], triXYZ[2][1]],[1,1,1]])
          coeff = numpy.linalg.solve(A, b)

          alfa = coeff[0]
          beta = coeff[1]
          gamma = coeff[2]

          zPoint = triXYZ[0][2] * alfa + triXYZ[1][2] * beta + triXYZ[2][2] * gamma

          return zPoint


      # Template Class Interface:
      # When using this class, make sure its name is set as the value of
      # the 'Class or Function to Process Features' transformer parameter
      class FeatureProcessor(object):
          def __init__(self):
              self.wallDict = {}
              self.roofDict = {}

          def input(self,feature): # This function is called every time a feature is added

              if feature.getAttribute('triangle'):
                  self.roofDict[feature.getAttribute('triID')] = feature
              else:
                  self.wallDict[feature.getAttribute('owOrder')] = feature

          def close(self):

              # Iterating over all walls to "lift" the higher coords to touch the roof
              for wallKey in self.wallDict:
                  wall = self.wallDict[wallKey]
                  wallDonut = False # To check if a geometry is donut
                  wallPolygon = False
                  wallFace = wall.getGeometry() # We get the geometry as a face
                  wallGeo = wallFace.getAsArea() # We need the "original" geometry

                  # Have not found a way of checking what geometry type the area is
                  # so using try to see if it is donut och polygon
                  try:
                      # Only outer boundary is interesting (i.e. openings not relevant)
                      wallDonut = wallGeo.getOuterBoundaryAsCurve()
                      pointList = wallDonut.getPoints()
                  except:
                      wallPolygon = wallGeo.getBoundaryAsCurve()
                      pointList = wallPolygon.getPoints()

                  # Handling both donuts and polygons in the same fashion
                  for tempPoint in xrange(len(pointList)):
                      tempXYZ = pointList[tempPoint].getXYZ()
                      if tempXYZ[2] > 0: # No ned to check ground level points

                          # Finding which roof triangle the point is inside
                          rt = triangleFinder(self.roofDict, tempXYZ)

                          # And finding the new z-value
                          zOff = zOffset(self.roofDict[rt], tempXYZ)

                          ###########################################################
                          # Need to check if first"last point is adjusted
                          ###########################################################

                          # To avoid adjusting z-vales that are e.g. higher part of door (since these are above ground)
                          ###########################################################
                          # Need to check roof thickness instead of hard coding
                          ###########################################################
                          if zOff - tempXYZ[2] < 1000:
                              pointList[tempPoint].setZ(zOff)


                  # Creating a new booundary. The boundary line is treated in the
                  # same way for both polygon and donut.
                  newFeature = fmeobjects.FMEFeature()
                  newLine = fmeobjects.FMELine([x.getXYZ() for x in pointList])
                  newFeature.setAttribute('wallOrderID', int(wallKey))

                  if wallPolygon:
                      newPoly = fmeobjects.FMEPolygon(newLine)
                      newFeature.setGeometry(newPoly)
                  else:
                      wallGeo.setOuterBoundaryCurve(newLine)
                      newFeature.setGeometry(wallGeo)
                      newFeature.setAttribute('donut', 'True')

                  self.pyoutput(newFeature)
    NEW_ATTRIBUTES = wallOrderID donut
    -> AttributeKeeper

Bookmark: Finding the door
  Extracts the geometry of the wall by rotating the wall surface with door and clipping the convex hull of the wall with the original wall, i.e. the door will be the remainder. Then rotating the door back.
Tester
    TEST_CLAUSE = TEST @Value(wallOrderID) = 4
    BOOL_OP = OR
    TEST_MODE = Automatic
    PASSED -> 3DRotator
3DRotator
    AXIS_CHOICE = Custom Axis
    YDIR = 1
    ANGLE = 90
    YORIG = 0
    XORIG = 0
    ZORIG = 0
    ZDIR = 0
    XDIR = 0
    ROTATED -> HullReplacer_2
    ROTATED -> Clipper [CLIPPER]
HullReplacer_2
    HULLTYPE_PARAM = Convex ()
    3DMODE_PARAM = Automatic
    HULL -> Clipper [CLIPPEE]
Clipper
    BOUNDARY_CASES = Treat as Inside
    LINES_AS_SEGMENTS = No
    CLIPPED_ATTR = _clipped
    ATTR_CONFLICT_RES = Use Clippee
    MISSING_VAL_MODE = Compute
    MEASURE_TYPE = Continuous
    CLIP_TYPE = Multiple Clippers
    PRESERVE_CLIPPEE_EXTENTS = No
    DEFAULT_VAL = 0
    VAL_SOURCE = Clippee Only
    CREATE_AGGREGATES = Yes
    CONNECT_Z_MODE = First Wins
    ATTR_ACCUM_MODE = Merge Clipper
    OUTSIDE -> 3DRotator_2
3DRotator_2
    AXIS_CHOICE = Y Axis
    ANGLE = 270
    ROTATED -> FeatureColorSetter_door
FeatureColorSetter_door
    COLOR = 0.666667,0.333333,0
    MODE = Fixed
    FILL_COLOR = 0.666667,0.333333,0
    COLORED -> AttributeCreator_door
    COLORED -> BoundsExtractor_2

Bookmark: To handle the wall with door
BoundsExtractor_2
    XMIN = _xmin
    -> 3DRotator_7
3DRotator_7
    AXIS_CHOICE = Custom Axis
    YDIR = 1
    ANGLE = 90
    YORIG = 0
    XORIG = @Value(_xmin)
    ZORIG = 0
    ZDIR = 0
    XDIR = 0
    ROTATED -> Clipper_2 [CLIPPER]
Tester_2
    TEST_CLAUSE = TEST @Value(wallOrderID) = 4
    BOOL_OP = OR
    TEST_MODE = Automatic
    PASSED -> Clipper_2 [CLIPPEE]
    FAILED -> 3DRotator_6
Clipper_2
    BOUNDARY_CASES = Treat as Inside
    LINES_AS_SEGMENTS = No
    CLIPPED_ATTR = _clipped
    ATTR_CONFLICT_RES = Use Clippee
    MISSING_VAL_MODE = Compute
    MEASURE_TYPE = Continuous
    CLIP_TYPE = Multiple Clippers
    PRESERVE_CLIPPEE_EXTENTS = No
    DEFAULT_VAL = 0
    VAL_SOURCE = Clippee Only
    CREATE_AGGREGATES = Yes
    CONNECT_Z_MODE = First Wins
    ATTR_ACCUM_MODE = Merge Clipper
    OUTSIDE -> 3DRotator_6

Bookmark: Finding windows and keeping walls
  Extracts the windows as holes in donuts and keeps the original walls.
Note: For windows ("up")
Note: For walls ("down")
Tester_Donut_walls
    TEST_CLAUSE = TEST @Value(donut) = True
    BOOL_OP = OR
    TEST_MODE = Automatic
    PASSED -> DonutHoleExtractor_walls
    PASSED -> SurfaceNormalCalculator
    FAILED -> SurfaceNormalCalculator
DonutHoleExtractor_walls
    DEAGGREGATE_INPUT = Yes
    HOLE -> FeatureColorSetter_windows
FeatureColorSetter_windows
    COLOR = 1,1,0.498039
    MODE = Fixed
    FILL_COLOR = 1,1,0.498039
    COLORED -> AttributeCreator_window

Bookmark: To get one wall per side.
  NB!!!!!!!!!!!!!!
  Check if this gives correct result for other buildings!
  Here assumed that walls are either vertical or horisontal (which seems common).
  If problems here, connect the input to this bookmark (Tester_Donut_Walls) directly
  to output of this bookmark (AttributeCreator_mainWalls)
SurfaceNormalCalculator
    Ok -> Aggregator
Aggregator
    ORDERED = No
    MODE = Geometry - Assemble One Level
    ACCUM_ATTRS_NAME = Merge Incoming Attributes
    SEP = ,
    GROUP_BY = normalY normalX
    AGGREGATE_TYPE = Homogeneous Collection (If Possible)
    AGGREGATE -> BoundsExtractor
    AGGREGATE -> Junction_7
Note: PythonCaller_wallExtender : Input
Junction_7
    -> Junction_8
Note: Aggregator : Aggregate
Junction_8
    -> PythonCaller_wallExtender
BoundsExtractor
    YMIN = _ymin
    YMAX = _ymax
    XMIN = _xmin
    XMAX = _xmax
    -> TestFilter_6
TestFilter_6
    DEFAULT_VALUE = <UNFILTERED>
    TEST_LIST = BOOL_OP,OR,COMPOSITE_TEST,<Unused>,TEST_CLAUSE,"TEST @Evaluate(@Value(_xmax)-@Value(_xmin)) < 0.1",Vertical,BOOL_OP,OR,COMPOSITE_TEST,<Unused>,TEST_CLAUSE,"TEST @Evaluate(@Value(_ymax)-@Value(_ymin)) < 0.1",Horisontal
    Vertical -> 3DRotator_3
    Horisontal -> 3DRotator_4
3DRotator_3
    AXIS_CHOICE = Custom Axis
    YDIR = 1
    ANGLE = 90
    YORIG = 0
    XORIG = @Value(_xmin)
    ZORIG = 0
    ZDIR = 0
    XDIR = 0
    ROTATED -> HullReplacer_4
HullReplacer_4
    HULLTYPE_PARAM = Convex ()
    3DMODE_PARAM = Automatic
    HULL -> Tester_2
3DRotator_6
    AXIS_CHOICE = Custom Axis
    YDIR = 1
    ANGLE = 270
    YORIG = 0
    XORIG = @Value(_xmin)
    ZORIG = 0
    ZDIR = 0
    XDIR = 0
    ROTATED -> PythonCaller_boundsReplacer
3DRotator_4
    AXIS_CHOICE = Custom Axis
    YDIR = 0
    ANGLE = 90
    YORIG = @Value(_ymin)
    XORIG = 0
    ZORIG = 0
    ZDIR = 0
    XDIR = 1
    ROTATED -> HullReplacer_3
HullReplacer_3
    HULLTYPE_PARAM = Convex ()
    3DMODE_PARAM = Automatic
    HULL -> 3DRotator_5
3DRotator_5
    AXIS_CHOICE = Custom Axis
    YDIR = 0
    ANGLE = 270
    YORIG = @Value(_ymin)
    XORIG = 0
    ZORIG = 0
    ZDIR = 0
    XDIR = 1
    ROTATED -> PythonCaller_boundsReplacer
PythonCaller_boundsReplacer
    PYTHONSYMBOL = FeatureProcessor
    PYTHONSOURCE:
      import fme
      import fmeobjects
      import math

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):

              for f in self.featureList:

                  f.setGeometry(f.getGeometry().getBoundaryAsCurve())
                  f.setAttribute('outerBoundary', True)

                  self.pyoutput(f)
    NEW_ATTRIBUTES = outerBoundary
    -> AttributeKeeper_7
AttributeKeeper_7
    KEEP_ATTRS = wallOrderID,outerBoundary
    -> PythonCaller_wallExtender
Note: Creates one wall surface per side by taking the / geometry from boundary line and extending the / polygons or donuts.
PythonCaller_wallExtender
    PYTHONSYMBOL = FeatureProcessor
    PYTHONSOURCE:
      import fme
      import fmeobjects
      import math

      # Template Class Interface:
      # When using this class, make sure its name is set as the value of
      # the 'Class or Function to Process Features' transformer parameter
      class FeatureProcessor(object):
          def __init__(self):
              self.polyDict = {}
              self.boundaryDict = {}

          def input(self,feature): # This function is called every time a feature is added
              if feature.getAttribute('outerBoundary'):
                  self.boundaryDict[feature.getAttribute('wallOrderID')] = feature
              else:
                  self.polyDict[feature.getAttribute('wallOrderID')] = feature


          def close(self):
              for key in self.polyDict:
                  wall = self.polyDict[key]
                  wallGeo = wall.getGeometry()
                  wallGeo = wallGeo.getPartAt(0)
                  boundary = self.boundaryDict[key]
                  boundaryGeo = boundary.getGeometry()
                  poly = True # If polygon

                  # Have not found a way of checking what geometry type the area is
                  # so using try to see if it is donut och polygon
                  try:
                      boundaryLine = wallGeo.getOuterBoundaryAsCurve()
                      poly = False
                  except:
                      boundaryLine = wallGeo.getBoundaryAsCurve()

                  if poly:
                      newPoly = fmeobjects.FMEPolygon(boundaryGeo)
                      wall.setGeometry(newPoly)
                  else:
                      wallGeo.setOuterBoundaryCurve(boundaryGeo)
                      wall.setGeometry(wallGeo)

                  self.pyoutput(wall)
    -> AttributeRenamer_2
FeatureColorSetter_walls_2
    COLOR = 0.666667,0.666667,0.498039
    MODE = Fixed
    FILL_COLOR = 0.666667,0.666667,0.498039
    COLORED -> Junction_9
    COLORED -> Junction_6
Note: AttributeCreator_mainWalls : Input
Junction_9
    -> Junction_10
Note: 2DForcer : Input
Junction_6
    -> Junction_13

Bookmark: Orientering reversed walls
  In the step where one wall per side is created (PythonCaller_wallExtender) some walls get reveresed orientation. These walls are corrected by comparing the surface normal from before and after the wallExtender and reversing the walls that have wrong orientation, i.e. after this all walls haev a surface normal pointing out of the house.
AttributeRenamer_2
    ATTR_TABLE:
      RENAME_SET_DEFAULT normalX > normX_org
      RENAME_SET_DEFAULT normalY > normY_org
      RENAME_SET_DEFAULT normalZ > normZ_org
    -> SurfaceNormalCalculator_2
SurfaceNormalCalculator_2
    Ok -> AttributeCreator_9
AttributeCreator_9
    ATTR_TABLE:
      SET_TO normDiffX = @Evaluate(@abs(@Value(normX_org)-@Value(normalX)))
      SET_TO normDiffY = @Evaluate(@abs(@Value(normY_org)-@Value(normalY)))
    -> TestFilter_9
TestFilter_9
    DEFAULT_VALUE = <UNFILTERED>
    TEST_LIST:
      BOOL_OP,AND,COMPOSITE_TEST,<Unused>,TEST_CLAUSE,"TEST @Value(normDiffX) < 0.1
      TEST @Value(normDiffY) < 0.1",correct
    correct -> CoordinateExtractor_5
    <UNFILTERED> -> Orientor
Orientor
    KIND = REVERSE
    FLIP_APPEARANCES_CHOICE = Yes
    ORIENTED -> CoordinateExtractor_5

Bookmark: Building height for each side (Almost hard coded....)
  The height of the intersection line between the faade plane and the 45 degree plane touching the highest part of teh roof is given as an attribute.
  WallHeightNEW and WallHeightOLD are according to the new suggested method and the current method in Sweden.
  When the building heigth is calculated later only the difference between the ground plane representing the mean ground elevation and the heigth given here (with an offset to get the heigth over the geoid) is calculated.
CoordinateExtractor_5
    Y_ATTR = _y
    IND = 0
    Z_ATTR = _z
    X_ATTR = _x
    MODE = All Coordinates
    LIST_NAME = _indices
    -> ListRangeExtractor_2
ListRangeExtractor_2
    MAX = _maxZvalue
    MIN = _minZvalue
    SRC_LIST = _indices{}.z
    -> PythonCaller_wallHeight_TEMP
PythonCaller_wallHeight_TEMP
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.featureDict = {}

          def input(self,feature):
              self.featureDict[feature.getAttribute('wallOrderID')] = feature

          def close(self):

              for wallKey in self.featureDict:

                  if wallKey == 2 or wallKey == 6:
                      wh = self.featureDict[wallKey].getAttribute('_maxZvalue')
                  else:
                      wh = self.featureDict[6].getAttribute('_maxZvalue')


                  self.featureDict[wallKey].setAttribute('wallHeightNEW', wh)
                  self.featureDict[wallKey].setAttribute('wallHeightOLD', self.featureDict[wallKey].getAttribute('_maxZvalue'))

                  self.pyoutput(self.featureDict[wallKey])
              else:
                  pass
    NEW_ATTRIBUTES = wallHeightNEW wallHeightOLD
    -> AttributeRounder_wallHeights
AttributeRounder_wallHeights
    SRC_ATTRS = wallHeightNEW wallHeightOLD
    ROUND_TYPE = Nearest
    PLACES = 0
    -> FeatureColorSetter_walls_2

Bookmark: To get SWEREF99 13 30
  Moving (to get origin in LL corner) and scaling to get meters.
  Setting reference system to SWEREF 99 13 30
  Removing all attributes (should adjust later to map and keep)
Offsetter
    ZOFF = 0
    MODE = Cartesian Coordinate
    YOFF = 6536
    XOFF = 9207
    OFFSET -> Scaler
Scaler
    XSCALE = 0.001
    TEXT_LOC_ONLY = Location and Size
    ZSCALE = 0.001
    YSCALE = 0.001
    RASTER_SCALING = Extents
    SCALE_ORIGIN = 0,0
    SCALED -> CoordinateSystemSetter
CoordinateSystemSetter
    COORDSYS = EPSG:3008
    -> AttributeKeeper_6
AttributeKeeper_6
    KEEP_ATTRS = wallHeightNEW,type,wallOrderID,wallHeightOLD
    -> AttributeKeeper_6_Output (output)
AttributeKeeper_6_Output (output)

Bookmark: Finding x,y of corners, Wall footprint
Note: FeatureColorSetter_walls_2 : Colored
Junction_13
    -> 2DForcer
    -> PythonCaller_RoofCutter
2DForcer
    2D -> HullAccumulator
HullAccumulator
    HULLTYPE_PARAM = Convex ()
    3DMODE_PARAM = 2D
    HULL -> Generalizer
Note: To remove points that are / not corner points.
Generalizer
    ALG_TEXT = Douglas (Generalize)
    TOLERANCE = 10
    PRESERVE = No
    -> CoordinateExtractor_4
CoordinateExtractor_4
    Y_ATTR = _y
    IND = 0
    Z_ATTR = _z
    X_ATTR = _x
    MODE = All Coordinates
    LIST_NAME = _indices
    -> AreaOnAreaOverlayer [AREA]

Bookmark: To get the part of the roofs inside the outer walls
AreaOnAreaOverlayer
    CONNECT_Z_MODE = First Wins
    DEAGGREGATE_INPUT = Yes
    OVC_ATTR = _overlaps
    ACCUM_ATTRS_NAME = Merge Incoming Attributes
    AREA -> TestFilter_8
TestFilter_8
    DEFAULT_VALUE = <UNFILTERED>
    TEST_LIST = BOOL_OP,OR,COMPOSITE_TEST,<Unused>,TEST_CLAUSE,"TEST @Value(_overlaps) > 1",mainRoof
    mainRoof -> PythonCaller_RoofCutter

Bookmark: Adding attribute to state if the roof surface should touch the higher or lower part of the roof
AttributeCreator_low
    ATTR_TABLE = SET_TO roofTouch = low
    -> PythonCaller_45degreePlane_lifter
AttributeCreator_high
    ATTR_TABLE = SET_TO roofTouch = high
    -> PythonCaller_45degreePlane_lifter

Bookmark: Creating 45 degree roof surface
CoordinateExtractor_6
    MODE = All Coordinates
    LIST_NAME = _indices
    -> ListRangeExtractor_3
    -> PythonCaller_Roof45degree
ListRangeExtractor_3
    MAX = _max_z
    MIN = _min_z
    SRC_LIST = _indices{}.z
    -> Aggregator_3
Aggregator_3
    ORDERED = No
    MODE = Geometry - Assemble One Level
    ACCUM_ATTRS_NAME = Use Attributes From One Feature
    SEP = ,
    AGGREGATE_TYPE = Homogeneous Collection (If Possible)
    LIST_ATTRS_TO_INCLUDE = _max_z _min_z
    LIST_NAME = z_list
    AGGREGATE -> AttributeCreator_12
AttributeCreator_12
    ATTR_TABLE = SET_TO aggr = 1
    -> PythonCaller_Roof45degree
PythonCaller_Roof45degree
    PYTHONSYMBOL = FeatureProcessor
    PYTHONSOURCE:
      import fme
      import fmeobjects
      from math import sqrt
      from math import tan
      from math import pi

      # Template Class Interface:
      # When using this class, make sure its name is set as the value of
      # the 'Class or Function to Process Features' transformer parameter
      class FeatureProcessor(object):
          def __init__(self):
              self.featureList = []
              self.high = []
              self.low = []

          def input(self,feature):
              if feature.getAttribute('aggr'):
                  self.high = feature.getAttribute('_max_z')
                  self.low = feature.getAttribute('_min_z')
              else:
                  self.featureList.append(feature)

          def close(self):
              try:
                  for r in self.featureList:

                      geo = r.getGeometry()
                      cu = geo.getBoundaryAsCurve()
                      pl = cu.getPoints()
                      colist = [tp.getXYZ() for tp in pl]
                      shortSeg = 999999 # To find length of shortest line seg
                      # Range -3 since we want the distance between current and next coordinate and the last and first coordinate is the same. So
                      # with -3 there is no need to check if the distance is zero.
                      for i in range(len(colist)-3):
                          dist = round(sqrt((colist[i][0]-colist[i+1][0])**2 + (colist[i][1]-colist[i+1][1])**2))
                          if dist < shortSeg:
                              shortSeg = dist

                      # New point list to get plane with 45 degree slope
                      newpl = []
                      for pnt in pl:
                          co = pnt.getXYZ()
                          # z offset for higher points will be same as horisontal dist to get 45 degree plan
                          if round(co[2]) == round(float(self.high)):
                              co = (co[0], co[1], shortSeg)
                          else:
                              co = (co[0], co[1], 0)
                          newpl.append(co)

                      nl = fmeobjects.FMELine(newpl)
                      np = fmeobjects.FMEPolygon(nl)
                      r.setGeometry(np)

                      r.setAttribute('45plane', True)

                      self.pyoutput(r)
              except:
                  pass
    NEW_ATTRIBUTES = 45plane
    -> PythonCaller_45degreePlane_lifter

Bookmark: Placing 45 degree plane at correct level
  Lifts the 45 degree plane to touch the top of the facade if roof angle <= 45 degrees
  Lifts the 45 degree plane to touch the top of the roof ridge if roof angle <= 45 degrees
  The minimum z-value of the 45 degree plane after placement is the intersection between 45 degree plane and facade plane.
PythonCaller_45degreePlane_lifter
    PYTHONSYMBOL = FeatureProcessor
    PYTHONSOURCE:
      import fme
      import fmeobjects
      from math import sqrt
      from math import tan
      from math import pi

      # Template Class Interface:
      # When using this class, make sure its name is set as the value of
      # the 'Class or Function to Process Features' transformer parameter
      class FeatureProcessor(object):
          def __init__(self):
              self.plane45 = []
              self.highAngle = False # If roof angle > 45 i.e. 45 degree plane touching roof top
              self.high = None
              self.low = None

          def input(self,feature):
              if feature.getAttribute('roofTouch'):
                  self.highAngle = feature.getAttribute('roofTouch') == 'high'
                  self.high = feature.getAttribute('_max_z')
                  self.low = feature.getAttribute('_min_z')
              elif feature.getAttribute('45plane'):
                  self.plane45.append(feature)

          def close(self):
              for r in self.plane45:

                  geo = r.getGeometry()
                  cu = geo.getBoundaryAsCurve()
                  pl = cu.getPoints()
                  colist = [tp.getXYZ() for tp in pl]
                  newpl = []

                  # If roof less than 45 degrees
                  if self.highAngle:
                      zOffset = float(self.high)
                  else:
                      zOffset = float(self.low)

                  for pnt in pl:
                      co = pnt.getXYZ()
                      # "Lifting" all points so lower side of plane is touching the top of the facade
                      co = (co[0], co[1], co[2] + zOffset)
                      newpl.append(co)

                  nl = fmeobjects.FMELine(newpl)
                  np = fmeobjects.FMEPolygon(nl)
                  r.setGeometry(np)

                  self.pyoutput(r)
    -> AttributeKeeper_45degreePlane

Bookmark: Lifting the 45 degree plane to touch the top of the dormer if dormer shall be included in building height
  Lifts the 45 degree plane to touch the top of the dormer (note dormer wall not roof edge of dormer)
  The minimum z-value of the 45 degree plane after placement is the intersection between 45 degree plane and facade plane.
AttributeKeeper_45degreePlane
    KEEP_ATTRS = ifc_unique_id,_countRoofArea
    -> CoordinateExtractor_45degreePlane
    -> PythonCaller_WallRoofAdjuster_2
CoordinateExtractor_45degreePlane
    MODE = All Coordinates
    LIST_NAME = _indices
    -> PythonCaller_TriangleSplitter_45degreePlane
PythonCaller_TriangleSplitter_45degreePlane
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.id = 0

          def input(self,feature):
              #self.featureList.append(feature)
              #Getting the list of coordinates
              xlist = feature.getAttribute('_indices{}.x')
              ylist = feature.getAttribute('_indices{}.y')
              zlist = feature.getAttribute('_indices{}.z')
              xlist = map(float, xlist)
              ylist = map(float,ylist)
              zlist = map(float, zlist)

              count = feature.getAttribute('_countRoofArea') # Need to add this attribute to merge with roofs later

              # Creating two triangles
              line1Points = [(xlist[0], ylist[0], zlist[0]), (xlist[1], ylist[1], zlist[1]), (xlist[2], ylist[2], zlist[2])]
              line2Points = [(xlist[2], ylist[2], zlist[2]), (xlist[3], ylist[3], zlist[3]), (xlist[4], ylist[4], zlist[4])]
              line1 = fmeobjects.FMELine(line1Points)
              line2 = fmeobjects.FMELine(line2Points)
              poly1 = fmeobjects.FMEPolygon(line1)
              poly2 = fmeobjects.FMEPolygon(line2)

              newFeature1 = fmeobjects.FMEFeature()
              newFeature1.setGeometry(poly1)
              newFeature1.setAttribute('triID', self.id)
              newFeature1.setAttribute('count', count)
              newFeature1.setAttribute('triangle', True)
              self.pyoutput(newFeature1)

              newFeature2 = fmeobjects.FMEFeature()
              newFeature2.setGeometry(poly2)
              newFeature2.setAttribute('triID', self.id+1)
              newFeature2.setAttribute('count', count)
              newFeature2.setAttribute('triangle', True)
              self.pyoutput(newFeature2)

              self.id += 2


          def close(self):
              pass
    NEW_ATTRIBUTES = triID count triangle
    -> PythonCaller_WallRoofAdjuster_2
Note: NB!!!! No output if dormer is lexx than 30% of wll width
PythonCaller_WallRoofAdjuster_2
    PYTHONSYMBOL = FeatureProcessor
    PYTHONSOURCE:
      import fme
      import fmeobjects
      import math
      import numpy

      # Finds in which triangle the point p is located
      # Strictly speadking findest the closest corner point
      # since we know that the point is inside one of the triangles.
      # roofTriangle = the roof triangles in self.roofList
      # p = (x,y,z) tuple with the coordinates of the point
      def triangleFinder(roofTriangle,p):
          shortDist = 99999999
          triID = -1 # Which roof triangel the point is inside
          for triKey in roofTriangle:
              tri = roofTriangle[triKey]
              if not triKey == tri.getAttribute('triID'):
                  break # Something wrong with indices
              triGeo = tri.getGeometry()
              triPoly = triGeo.getBoundaryAsCurve()
              triPoints = triPoly.getPoints()

              for tempPoint in triPoints:
                  xyz = tempPoint.getXYZ()
                  tempDist = math.sqrt((xyz[0]-p[0])**2 + (xyz[1]-p[1])**2)
                  if tempDist < shortDist:
                      shortDist = tempDist
                      triID = triKey

          return triID



      # Calculating the offset of the z-coordinate
      # tri = current triangle
      # point = current point
      def zOffset(tri, point):
          # To get (x,y,z) tuples from the triangle
          triGeo = tri.getGeometry()
          triPoly = triGeo.getBoundaryAsCurve()
          triPoints = triPoly.getPoints()
          triPoints = triPoints[:3] # Last point is same as first point

          triXYZ = [x.getXYZ() for x in triPoints]

          b = numpy.array([[point[0]],[point[1]],[1]])
          A = numpy.array([[triXYZ[0][0], triXYZ[1][0], triXYZ[2][0]],[triXYZ[0][1], triXYZ[1][1], triXYZ[2][1]],[1,1,1]])
          coeff = numpy.linalg.solve(A, b)

          alfa = coeff[0]
          beta = coeff[1]
          gamma = coeff[2]

          zPoint = triXYZ[0][2] * alfa + triXYZ[1][2] * beta + triXYZ[2][2] * gamma

          return zPoint


      # Template Class Interface:
      # When using this class, make sure its name is set as the value of
      # the 'Class or Function to Process Features' transformer parameter
      class FeatureProcessor(object):
          def __init__(self):
              self.wall = []              # For the wall incl. coordinates of dormer top
              self.roof = []              # For the 45 degree plane
              self.roofTriangles = {}     # For the roof triangles

          def input(self,feature): # This function is called every time a feature is added

              if feature.getAttribute('isWall'):
                  self.wall.append(feature)
              elif feature.getAttribute('triangle'):
                  self.roofTriangles[feature.getAttribute('triID')] = feature
              else:
                  self.roof.append(feature)

          def close(self):

              # Only  included dormers occupying 30% or more of the width of the wall
              if float(self.wall[0].getAttribute('dormerTopX')) >= 30:

                  # Coordinates of top of dormer
                  dtx = float(self.wall[0].getAttribute('dormerTopX'))
                  dty = float(self.wall[0].getAttribute('dormerTopY'))
                  dtz = float(self.wall[0].getAttribute('dormerTopZ'))

                  # Find in which roof triangle the dormer top is located
                  dormerTriangle = triangleFinder(self.roofTriangles, (dtx, dty, dtz))

                  # Find z of the current position of teh 45 degree plane.
                  currentZ = zOffset(self.roofTriangles[dormerTriangle], (dtx, dty, dtz))

                  # Finding offset to dormer top z
                  zo = dtz - currentZ


                  # Lifting the 45 degree plane to touch the top of the dormer
                  for r in self.roof:
                      geo = r.getGeometry()
                      cu = geo.getBoundaryAsCurve()
                      pl = cu.getPoints()
                      colist = [tp.getXYZ() for tp in pl]
                      newpl = []
                      for pnt in pl:
                          co = pnt.getXYZ()
                          # "Lifting" all points so lower side of plane is touching the top of the facade
                          co = (co[0], co[1], co[2] + zo)
                          newpl.append(co)

                      nl = fmeobjects.FMELine(newpl)
                      np = fmeobjects.FMEPolygon(nl)
                      r.setGeometry(np)

                      self.pyoutput(r)
    NEW_ATTRIBUTES = wallOrderID donut

FME custom transformer WallsTo2D_Python

SurfaceFootprintReplacer_3_Input (input)
    -> SurfaceFootprintReplacer_3
Note: To get 2D. / Gives a geometry (IFMELine) that is easier to handle / later compared to 2DForcer.
SurfaceFootprintReplacer_3
    OFFSET_Z = 0
    SHADOW_MODE = Overhead Shadow
    FOOTPRINT -> CoordinateExtractor_3
    <REJECTED> -> SurfaceFootprintReplacer_3__Rejected_
SurfaceFootprintReplacer_3__Rejected_: Inspector
CoordinateExtractor_3
    MODE = All Coordinates
    LIST_NAME = _indices
    -> AttributeCreator_3
AttributeCreator_3
    ATTR_TABLE:
      SET_TO _x_end_wall
      SET_TO _y_end_wall
      SET_TO _x_start_wall
      SET_TO _y_start_wall
      SET_TO _y_min
      SET_TO _y_max
    -> PythonCaller_max_x
Note: Tried to add both max and min x in the / same caller but it gave overflow error
PythonCaller_max_x
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outMax = {} # key = uuid, value = max coordinate
          outMin = {} # key = uuid, value = min coordinate
          for wall in lines:

              i = 0 # Index
              tmx = -99999999 # Temporary max x coordinate
              #tminx = float('inf') # Temporary min x coordinate
              tuuid = wall.getAttribute('_uuid') # Current UUID
              while True:
                  tx = wall.getAttribute('_indices{%d}.x' % i) # Current x coordinate
                  if tx == None:
                      break
                  if tx > tmx:
                      tmx = tx
                  #elif tx < tminx:
                      #tminx = tx
                  i += 1

              outMax[tuuid] = int(round(tmx))
              #outMin[tuuid] = round(tminx)
          return outMax #, outMin

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              # Tried with both max and min but got error (overflow in setAttribute)
              #maxX, minX = lineEndsFinder(self.featureList) # Returns dict with key:uuid; value:maxX
              maxX = lineEndsFinder(self.featureList) # Returns dict with key:uuid; value:maxX
              for f in self.featureList:
                  fuuid = f.getAttribute('_uuid') # uuid to use as key in the maxX dictionary
                  f.setAttribute("_x_end_wall", maxX[fuuid])
                  #f.setAttribute("_x_start_wall", minX[fuuid])
                  self.pyoutput(f)
    NEW_ATTRIBUTES = _x_end_wall
    -> PythonCaller_min_x
PythonCaller_min_x
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outMin = {} # key = uuid, value = min coordinate
          for wall in lines:

              i = 0 # Index
              tminx = float('inf') # Temporary min x coordinate
              tuuid = wall.getAttribute('_uuid') # Current UUID
              while True:
                  tx = wall.getAttribute('_indices{%d}.x' % i) # Current x coordinate
                  if tx == None:
                      break
                  if tx < tminx:
                      tminx = tx
                  i += 1

              outMin[tuuid] = int(round(tminx))
          return outMin

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              minX = lineEndsFinder(self.featureList) # Returns dict with key:uuid; value:maxX
              for f in self.featureList:
                  fuuid = f.getAttribute('_uuid') # uuid to use as key in the maxX dictionary
                  f.setAttribute("_x_start_wall", minX[fuuid])
                  self.pyoutput(f)
    NEW_ATTRIBUTES = _x_start_wall
    -> PythonCaller_max_y
PythonCaller_max_y
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outMax = {} # key = uuid, value = min coordinate
          for wall in lines:

              i = 0 # Index
              tmy = -9999 # Temporary min x coordinate
              tuuid = wall.getAttribute('_uuid') # Current UUID
              while True:
                  ty = wall.getAttribute('_indices{%d}.y' % i) # Current x coordinate
                  if ty == None:
                      break
                  if ty > tmy:
                      tmy = ty
                  i += 1

              outMax[tuuid] = int(round(tmy))
          return outMax

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              maxY = lineEndsFinder(self.featureList) # Returns dict with key:uuid; value:maxX
              for f in self.featureList:
                  fuuid = f.getAttribute('_uuid') # uuid to use as key in the maxX dictionary
                  f.setAttribute("_y_max", maxY[fuuid])
                  self.pyoutput(f)
    NEW_ATTRIBUTES = _y_max
    -> PythonCaller_min_y
PythonCaller_min_y
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outMin = {} # key = uuid, value = min coordinate
          for wall in lines:

              i = 0 # Index
              tminy = float('inf') # Temporary min x coordinate
              tuuid = wall.getAttribute('_uuid') # Current UUID
              while True:
                  ty = wall.getAttribute('_indices{%d}.y' % i) # Current x coordinate
                  if ty == None:
                      break
                  if ty < tminy:
                      tminy = ty
                  i += 1

              outMin[tuuid] = int(round(tminy))
          return outMin

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              minY = lineEndsFinder(self.featureList) # Returns dict with key:uuid; value:maxX
              for f in self.featureList:
                  fuuid = f.getAttribute('_uuid') # uuid to use as key in the maxX dictionary
                  f.setAttribute("_y_min", minY[fuuid])
                  self.pyoutput(f)
    NEW_ATTRIBUTES = _y_min
    -> PythonCaller_start_end_y
PythonCaller_start_end_y
    PYTHONSYMBOL = FeatureProcessor
    PYTHONSOURCE:
      import fme
      import fmeobjects
      # Template Function interface:
      # When using this function, make sure its name is set as the value of
      # the 'Class or Function to Process Features' transformer parameter
      def processFeature(feature):
          pass

      def lineEndsFinder(lines):
          outY = {} # key = uuid, value = min coordinate
          for wall in lines:

              tuuid = wall.getAttribute('_uuid') # Current UUID
              startX = wall.getAttribute('_x_start_wall')
              endX = wall.getAttribute('_x_end_wall')
              minY = wall.getAttribute('_y_min')
              maxY = wall.getAttribute('_y_max')

              if startX == endX:
                  startY = minY
                  endY = maxY
              elif minY == maxY:
                  startY = minY
                  endY = maxY
              else:
                  i = 0 # Index of coordinate
                  while True:
                      tx = wall.getAttribute('_indices{%d}.x' % i) # Current x coordinate
                      ty = wall.getAttribute('_indices{%d}.y' % i) # Current y coordinate
                      if tx == None:
                          break
                      else:
                          # This cannot be done where the attributes are read since the last will be a None object
                          tx = int(round(tx))
                          ty = int(round(ty))
                      if tx == startX:
                          if ty == minY:
                              startY = minY
                              endY = maxY
                          elif ty == maxY:
                              startY = maxY
                              endY = minY
                      i += 1

              outY[tuuid] = (startY, endY)
              starY = None
              endY = None

          return outY

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              startEndY = lineEndsFinder(self.featureList) # Returns dict with key:uuid; value:maxX
              for f in self.featureList:
                  fuuid = f.getAttribute('_uuid') # uuid to use as key in the maxX dictionary
                  f.setAttribute("_y_start_wall", startEndY[fuuid][0])
                  f.setAttribute("_y_end_wall", startEndY[fuuid][1])
                  self.pyoutput(f)
    NEW_ATTRIBUTES = _y_start_wall _y_end_wall
    -> AttributeRemover
AttributeRemover
    REMOVE_ATTRS = _y_max,_y_min
    -> CoordinateExtractor_End_Wall_Output (output)
CoordinateExtractor_End_Wall_Output (output)
CoordinateCounter
    CNT_ATTR = _coordcount_wall
    -> CoordinateExtractor_Start_Wall
CoordinateExtractor_Start_Wall
    Y_ATTR = _y_start_wall
    IND = 0
    Z_ATTR = _z_start_wall
    X_ATTR = _x_start_wall
    MODE = Specify Coordinate
    -> CoordinateExtractor_End_Wall
CoordinateExtractor_End_Wall
    Y_ATTR = _y_end_wall
    IND = @Value(_coordcount_wall)-1
    Z_ATTR = _z_end_wall
    X_ATTR = _x_end_wall
    MODE = Specify Coordinate

Bookmark: Walls -> 2D and finding start and end coordinates
Note: Need IFMELine geometry later and for that the SurfaceFootPrintReplacer is better BUT some walls becomes polygons instead of lines. How to handle? / Coordinates extracted to be able to handle line directions later.

FME custom transformer AreaComplianceCheck

Parameters:
- zOffset2 = 20   # " " Attribute Value
- GML_PARENT_PROPERTY = @Value(gml_parent_property)   # Gml Parent Property
- _AREA = @Value(_area)   # Area

Offsetter_Input (input)
    -> Offsetter
Offsetter
    ZOFF = 0
    MODE = Cartesian Coordinate
    YOFF = 6536
    XOFF = 9207
    OFFSET -> Scaler
Scaler
    XSCALE = 0.001
    TEXT_LOC_ONLY = Location and Size
    ZSCALE = 0.001
    YSCALE = 0.001
    RASTER_SCALING = Extents
    SCALE_ORIGIN = 0,0
    SCALED -> CoordinateSystemSetter
CoordinateSystemSetter
    COORDSYS = EPSG:3008
    -> AttributeCreator_Offset_2
AttributeCreator_Offset_2
    ATTR_TABLE = SET_TO zOffset = $(zOffset2)
    -> Offsetter_3
Offsetter_3
    ZOFF = @Value(zOffset)
    MODE = Cartesian Coordinate
    YOFF = 6239396
    XOFF = 92770
    OFFSET -> Rotator_2
Rotator_2
    ANGLE = 156
    YORIG = 6239396
    XORIG = 92770
    ROTATED -> Clipper_2 [CLIPPER]
Clipper_2_Clippee (input)
    -> Clipper_2 [CLIPPEE]
Clipper_2
    BOUNDARY_CASES = Treat as Inside
    LINES_AS_SEGMENTS = No
    CLIPPED_ATTR = _clipped
    ATTR_CONFLICT_RES = Use Clippee
    MISSING_VAL_MODE = Compute
    MEASURE_TYPE = Continuous
    CLIP_TYPE = Multiple Clippers
    PRESERVE_CLIPPEE_EXTENTS = No
    DEFAULT_VAL = 0
    VAL_SOURCE = Clippee Only
    CREATE_AGGREGATES = Yes
    CONNECT_Z_MODE = First Wins
    ATTR_ACCUM_MODE = Merge Clipper
    INSIDE -> AttributeCreator
AttributeCreator
    ATTR_TABLE = SET_TO AreaOk
    -> PythonCaller
PythonCaller
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.byggnadsArea = None
              self.fe = None
              self.maxByggnadsArea = None
              self.logger = fmeobjects.FMELogFile()

          def input(self,feature): # This function is called every time a feature is added
              if feature.getAttribute('gml_parent_property') == 'egenskapsbestammelse':
                  self.logger.logMessageString("AREA CHECK")
                  self.maxByggnadsArea = float(feature.getAttribute('variabel{0}.DP_VarDecimaltal.varde'))
                  self.logger.logMessageString(str(self.maxByggnadsArea))
                  self.fe = feature

              else:
                  self.byggnadsArea = feature.getAttribute('_area')
                  self.logger.logMessageString(str(self.byggnadsArea))

          def close(self):
              # Checing if the building is lower than the allowed height with the
              # allowed toleracne of 10 cm.
              if self.byggnadsArea > self.maxByggnadsArea:
                  self.fe.setAttribute('AreaOk', False)
                  self.logger.logMessageString('AreaOk False')
              else:
                  self.fe.setAttribute('AreaOk', True)
                  self.logger.logMessageString('AreaOk True')

              self.pyoutput(self.fe)
    -> Tester_Passed (output)
Tester_Passed (output)

FME custom transformer CreateBasisBYA

Parameters:
- IFC_UNIQUE_ID = @Value(ifc_unique_id)   # Ifc Unique Id

Bookmark: BasisBYA
Input_storey (input)
    -> MinZ_2
MinZ_2
    -> SurfaceFootprintReplacer_3
SurfaceFootprintReplacer_3
    OFFSET_Z = @Value(_zminval)
    SHADOW_MODE = Overhead Shadow
    FOOTPRINT -> Snapper
Input_pointCloud (input)
    -> MinZ
Input_facade (input)
    -> MinZ
MinZ
    -> SurfaceFootprintReplacer_2
SurfaceFootprintReplacer_2
    OFFSET_Z = @Value(_zminval)
    SHADOW_MODE = Overhead Shadow
    FOOTPRINT -> HullAccumulator
    <REJECTED> -> SurfaceFootprintReplacer_2__Rejected_
HullAccumulator
    GROUP_BY = ifc_unique_id _zminval
    HULLTYPE_PARAM = Convex ()
    3DMODE_PARAM = 3D
    DEFAULTZ = @Value(_zminval)
    HULL -> Snapper
Dissolver_2
    ACCUM_INPUT_ATTRS = Merge Incoming Attributes
    NO_OVRLP = No
    CONNECT_Z_MODE = Extend
    DEAGGREGATE_INPUT = Yes
    AREA -> BoundsExtractor
BoundsExtractor
    YMIN = _ymin
    ZMIN = _zmin
    YMAX = _ymax
    ZMAX = _zmax
    XMIN = _xmin
    XMAX = _xmax
    -> SurfaceFootprintReplacer
SurfaceFootprintReplacer
    OFFSET_Z = @Value(_zminval)
    SHADOW_MODE = Overhead Shadow
    FOOTPRINT -> DonutHoleExtractor_2
DonutHoleExtractor_2
    DEAGGREGATE_INPUT = Yes
    OUTERSHELL -> Output (output)
Output (output)
SurfaceFootprintReplacer_2__Rejected_: Inspector [off]

Bookmark: Prepare for dissolve
  Snapp areas that won't dissolve (because they don't intersect/ are connected)
Snapper
    SNAPTYPE_PARAM = Segment Snapping
    TOLERANCE = 10
    CLEANING_TOLERANCE_MODE = AUTO
    SNAPPED -> Dissolver_2
    UNTOUCHED -> Dissolver_2

FME custom transformer Building_Clipper

Parameters:
- IFC_PARENT_UNIQUE_ID = @Value(ifc_parent_unique_id)   # Ifc Parent Unique Id
- DISTANCE = 10   # Distance
- OFFSET_Z = 0   # Z" Elevation

Input (input)
    -> Deaggregator
    -> BoundsExtractor
    -> BoundingBoxAccumulator
    -> Input
BoundingBoxAccumulator
    DESTINATION_SCALE = 1
    SOURCE_SCALE = 1
    TOPFER_INDEX = No
    ATTR_NAME = _topferIndex
    ACCUM_ATTRS_NAME = Use Attributes From One Feature
    BOUNDING_BOX -> FeatureMerger [REQUESTOR]
BoundsExtractor
    YMIN = _ymin
    ZMIN = _zmin
    YMAX = _ymax
    ZMAX = _zmax
    XMIN = _xmin
    XMAX = _xmax
    -> ListBuilder
ListBuilder
    LIST_ATTRS_TO_INCLUDE = _zmin ifc_parent_unique_id
    GROUPS_ORDERED = No
    LIST_NAME = _list
    -> ListRangeExtractor
ListRangeExtractor
    MAX = _max
    MIN = _min
    SRC_LIST = _list{}._zmin
    -> FeatureMerger [SUPPLIER]
FeatureMerger
    REJECT_NULL_MISSING_KEYS = No
    PROCESS_DUPS = No
    ATTR_CONFLICT_RES = Use Requestor
    MERGE_TYPE = Attributes Only
    JOIN_KEYS = @Value(ifc_parent_unique_id) @Value(_list{0}.ifc_parent_unique_id) AUTO
    SUPPLIERS_FIRST = No
    IGNORE_NULLS = No
    ATTR_ACCUM_MODE = Merge Supplier
    MERGED -> SurfaceFootprintReplacer
SurfaceFootprintReplacer
    OFFSET_Z = $(OFFSET_Z)+@Value(_min)
    SHADOW_MODE = Overhead Shadow
    FOOTPRINT -> Extruder
Extruder
    DISTANCE = $(DISTANCE)
    DIRECTION = Vertical
    EXTRUDED -> Clipper_2 [CLIPPER]
    EXTRUDED -> Output_extruded (output)
Output_extruded (output)
Deaggregator
    GEOM_NAME_FIELD = _geometry_name
    CHILD_ID_ATTR = _hierarchy_child_id_list
    COPY_ATTR = Every Node
    LIST_ATTR_MODE_LOOKUP = LEAN
    PARENT_ID_ATTR = _hierarchy_parent_id
    MODE = Flatten One Level
    ID_ATTR = _hierarchy_id
    EXPLODE_INSTANCES = No
    PART_NUMBER_FIELD = _part_number
    ID_SELECTION = ID and Parent ID
    SPLIT_COMPOSITES = No
    DEAGGREGATED -> GeometryFilter
GeometryFilter
    GEOM_PORT_NAMES = Solid
    BREAK_AGG = No
    SOLID -> Clipper_2 [CLIPPEE]
Clipper_2
    BOUNDARY_CASES = Treat as Inside
    LINES_AS_SEGMENTS = No
    CLIPPED_ATTR = _clipped
    MISSING_VAL_MODE = Compute
    MEASURE_TYPE = Continuous
    CLIP_TYPE = Multiple Clippers
    PRESERVE_CLIPPEE_EXTENTS = No
    VAL_SOURCE = Clippee Only
    CREATE_AGGREGATES = Yes
    INSIDE -> Output_clipper (output)
    <REJECTED> -> Rejected (output)
Output_clipper (output)
Rejected (output)
Input: Inspector [off]

FME custom transformer IFC2CityGML_Geometryconverter_parts

GeometryPartExtractor_2_Input (input)
    -> GeometryPartExtractor_2
Note: Check that geometry name is solid
GeometryPartExtractor_2
    GQUERY:
      for $geom in //geometry
      where $geom/@fme_geometry_name = 'Body'
      return number($geom/@fme_id)
    EXTRACTTYPE_PARAM = Extract
    PROCESSED -> GeometryCoercer_2
    UNTOUCHED -> GeometryCoercer_2
Note: Check for geometry type IFMEExtrusion OR IFMEBRepSolid
GeometryCoercer_2
    GQUERY:
      for $geom in //geometry
      where $geom/@fme_geometry_type = 'IFMEExtrusion'
      or $geom/@fme_geometry_type = 'IFMEBRepSolid'
      return number($geom/@fme_id)
    KIND = fme_composite_surface
    COERCED -> Deaggregator
    UNTOUCHED -> Deaggregator
Note: Changed split compostites to YES
Deaggregator
    GEOM_NAME_FIELD = _geometry_name
    LIST_ATTR_MODE_LOOKUP = LEAN
    MODE = Flatten All Levels
    EXPLODE_INSTANCES = No
    SPLIT_COMPOSITES = Yes
    DEAGGREGATED -> GeometryRefiner
Note: Keep this or not?
GeometryRefiner
    -> Output (output)
Output (output)

FME custom transformer SlopeCalculator
This transformer calculates the slope of input polygons and surfaces.
It works by extracting the bounds of an input feature and comparing its maximum and minimum Z values. 
- If the difference is 0, then the surface is deemed flat with zero slope.
- If the difference is not zero, then the input feature is triangulated, and the slope of each of its triangles is calculated. The slope is presented as the average of the slopes of its triangles.
Input Ports 
    Input 
Input features must have geometry of type polygon or surface.
    Output Ports 
    Output 
Features are output with a new attribute with the slope of source data. 
_slope: Contains the value of slope in degrees.
    <Rejected> 
Features will be passed through this port if they are not of type polygon (area, ellipse) or surface. The attribute fme_rejection_code will be added to each feature with value INVALID_GEOMETRY_TYPE.
    Parameters 
This transformer has no parameters.
    Usage Notes
For best results, make sure that input surfaces are planar.

Input (input)
    -> GeometryFilter
Counter
    SCOPE = Local
    CNT_ATTR = SC_count
    DOMAIN = SC_count
    START = 0
    -> BoundsExtractor_2
Note: Extract face bounds
BoundsExtractor_2
    YMIN = _ymin
    ZMIN = _zmin
    YMAX = _ymax
    ZMAX = _zmax
    XMIN = _xmin
    XMAX = _xmax
    -> Tester_2
Note: Determine if surface is flat or sloped
Tester_2
    TEST_CLAUSE = TEST @Value(_zmin) = @Value(_zmax)
    BOOL_OP = OR
    TEST_MODE = Automatic
    PASSED -> AttributeCreator_4
    FAILED -> Triangulator
    FAILED -> FeatureMerger [REQUESTOR]
Note: Flat surfaces simply get 0 for slope
AttributeCreator_4
    ATTR_TABLE = SET_TO SLOPE = 0
    -> AttributeManager
Note: Add the calculated slope / to the original faces
FeatureMerger
    PROCESS_DUPS = No
    ATTR_CONFLICT_RES = Use Requestor
    MERGE_TYPE = Attributes Only
    JOIN_KEYS = @Value(SC_count) @Value(SC_count) AUTO
    SUPPLIERS_FIRST = No
    IGNORE_NULLS = Yes
    ATTR_ACCUM_MODE = Merge Supplier
    MERGED -> AttributeManager
Note: Clean up features
AttributeManager
    ATTR_TABLE:
      REMOVE SC_count
      REMOVE _xmax
      REMOVE _xmin
      REMOVE _ymax
      REMOVE _ymin
      REMOVE _zmax
      REMOVE _zmin
      RENAME_SET_VALUE SLOPE > _slope
    -> Output (output)
Output (output)
<Rejected> (output)

Bookmark: Validate geometry
GeometryFilter
    GEOM_PORT_NAMES = Area Ellipse Surface
    BREAK_AGG = No
    AREA -> Counter
    ELLIPSE -> Counter
    SURFACE -> Counter
    <UNFILTERED> -> AttributeCreator_5
AttributeCreator_5
    ATTR_TABLE = SET_TO fme_rejection_code = INVALID_GEOMETRY_TYPE
    -> <Rejected> (output)

Bookmark: Replace faces with triangles
Triangulator
    TRIANGLES -> Deaggregator_2
Deaggregator_2
    GEOM_NAME_FIELD = _geometry_name
    LIST_ATTR_MODE_LOOKUP = LEAN
    MODE = Flatten One Level
    EXPLODE_INSTANCES = No
    PART_NUMBER_FIELD = _part_number
    SPLIT_COMPOSITES = Yes
    DEAGGREGATED -> GeometryCoercer
GeometryCoercer
    KIND = fme_polygon
    CHECKZ = No
    COERCED -> CoordinateExtractor_2

Bookmark: Extract coordinates of the triangle vertices
CoordinateExtractor_2
    Y_ATTR = _y0
    IND = 0
    Z_ATTR = _z0
    X_ATTR = _x0
    MODE = Specify Coordinate
    Z_DEFAULT = -9999
    -> CoordinateExtractor_3
CoordinateExtractor_3
    Y_ATTR = _y1
    IND = 1
    Z_ATTR = _z1
    X_ATTR = _x1
    MODE = Specify Coordinate
    Z_DEFAULT = -9999
    -> CoordinateExtractor_4
CoordinateExtractor_4
    Y_ATTR = _y2
    IND = 2
    Z_ATTR = _z2
    X_ATTR = _x2
    MODE = Specify Coordinate
    Z_DEFAULT = -9999
    -> AttributeCreator

Bookmark: Calculate slopes
Note: Create two vectors that / connect the triangle's / vertices (from one vertex / to the other two)
AttributeCreator
    ATTR_TABLE:
      SET_TO _u1 = @Evaluate(@Value(_x0)-@Value(_x2))
      SET_TO _v1 = @Evaluate(@Value(_x1)-@Value(_x2))
      SET_TO _u2 = @Evaluate(@Value(_y0)-@Value(_y2))
      SET_TO _v2 = @Evaluate(@Value(_y1)-@Value(_y2))
      SET_TO _u3 = @Evaluate(@Value(_z0)-@Value(_z2))
      SET_TO _v3 = @Evaluate(@Value(_z1)-@Value(_z2))
    -> AttributeCreator_2
Note: Take a cross product of the / two vectors to find a vector / that is normal to the triangle
AttributeCreator_2
    ATTR_TABLE:
      SET_TO _nx = @Evaluate(@Value(_u2)*@Value(_v3)-@Value(_u3)*@Value(_v2))
      SET_TO _ny = @Evaluate(@Value(_u3)*@Value(_v1)-@Value(_u1)*@Value(_v3))
      SET_TO _nz = @Evaluate(@Value(_u1)*@Value(_v2)-@Value(_u2)*@Value(_v1))
    -> AttributeCreator_3
Note: Find the length of the normal's / projection on the x,y plane
AttributeCreator_3
    ATTR_TABLE = SET_TO _length = @Evaluate(@sqrt(@Value(_nx)*@Value(_nx)+@Value(_ny)*@Value(_ny)))
    -> AttributeCreator_6
Note: Find the triangle's slope: / - First find the absolute value / of its normal's slope. / - A plane's normal is perpendicular / to that plane, hence their slope / differs by 90 degrees (PI/2 radians)
AttributeCreator_6
    ATTR_TABLE = SET_TO _slope = @Evaluate(3.14159/2.0-@atan2(@abs(@Value(_nz)),@abs(@Value(_length))))
    -> AttributeCreator_7
Note: Convert from / radians to degrees
AttributeCreator_7
    ATTR_TABLE = SET_TO SLOPE = @Evaluate(@Value(_slope)*180.0/3.14159)
    -> StatisticsCalculator
Note: Find the average
StatisticsCalculator
    MEAN_ATTR = SLOPE
    COMPUTE_HISTOGRAM = NO
    STATS_ATTRS = SLOPE
    GROUP_BY = SC_count
    PREPEND_ATTR_NAME_CHOICE = For multiple results only
    SUMMARY -> FeatureMerger [SUPPLIER]

FME custom transformer detaljPlanReader

Parameters:
- XML_PARENT_CHILD_POS = @Value(xml_parent_child_pos)   # Xml Parent Child Pos
- DP_OMRADE.ID = @Value(DP_Omrade.id)   # Dp Omrade.id
- UUID = @Value(uuid)   # uuid
- GML_ID = @Value(gml_id)   # Gml Id
- XML_PARENT_ID = @Value(xml_parent_id)   # Xml Parent Id
- ANVANDNINGSSLAG = @Value(anvandningsslag)   # anvandningsslag
- PLUS.HREF = @Value(plus.href)   # plus.href
- MINUS.HREF = @Value(minus.href)   # minus.href
- OMRADE.XLINK_HREF = @Value(omrade.xlink_href)   # Omrade.xlink Href
- BETECKNING = @Value(beteckning)   # beteckning
- BESTAMMELSETYP = @Value(bestammelsetyp)   # bestammelsetyp
- XML_ID = @Value(xml_id)   # Xml Id
- URSPRUNGLIG = @Value(ursprunglig)   # ursprunglig

Aggregator_Input (input)
    -> Aggregator
Note: Create list with gränser per område
Aggregator
    ORDERED = No
    MODE = Attributes Only
    ACCUM_ATTRS_NAME = Merge Incoming Attributes
    SEP = ,
    GROUP_BY = xml_parent_id
    LIST_ATTRS_TO_INCLUDE = minus.href plus.href xml_parent_child_pos
    LIST_NAME = childList
    AGGREGATE -> PolygonCreator
AttributeCreator_2_Input (input)
    -> AttributeCreator_2
Note: Create ID for later join
AttributeCreator_2
    ATTR_TABLE = SET_TO ID_join = #@Value(gml_id)
    -> PolygonCreator
Note: Creates polygons over Områden.
PolygonCreator: PythonCaller
    PYTHONSYMBOL = FeatureProcessor
    PYTHONSOURCE:
      import fme
      import fmeobjects

      # Finds and returns the requested gräns
      def gransFinder(id,gransList):
          for grans in gransList:
              if grans.getAttribute('ID_join') == id:
                  return grans

      # Finds first line segment in a boundary, either outer or inner polygon
      def initialBoundaryLine(polygonBoundaryParts):
          geo = polygonBoundaryParts.getGeometry()

          nbrLines = geo.numParts()

          # Taking first part of the FMEPath
          polygonBoundary = geo.getPartAt(0)

          if type(polygonBoundary) == fmeobjects.FMEArc:
              polygonBoundary = polygonBoundary.getAsLine()

          # Iterating over the parts in the FMEPath object
          for tp in xrange(1,nbrLines):
              tpl = geo.getPartAt(tp) # Next part (at index tp)

              # Needs to be an FMELine
              if type(tpl) == fmeobjects.FMEArc:
                  tpl = tpl.getAsLine()

              polygonBoundary.appendLine(tpl)

          return polygonBoundary

      # #################################################################
      # FeatureProcessor
      # #################################################################
      class FeatureProcessor(object):
          def __init__(self):
              self.omrade = []
              self.grans = []

          # Saving in different lists depending on if the feature is a gräns or område
          def input(self,feature):
              if feature.hasGeometry():
                  self.grans.append(feature)
              else:
                  self.omrade.append(feature)

          def close(self):

              # Iterating over all Områden sent to the PythonCaller
              for omr in self.omrade:
                  boundaryList = []
                  tempGrans = True # Will stop the loop after last item is found (temp = None)
                  index = 0 # Index of "Gräns"
                  innerIndex = 0 # For keeping track of holes
                  firstLine = True # If first line segment of a gräns

                  #Looping over all "gränser" in current "Område"
                  while tempGrans != None:
                      tempGrans = omr.getAttribute('childList{%i}.xml_parent_child_pos' % (index))

                      # Already found last "gräns" of the "område"
                      if not tempGrans:
                          break
                      tempGrans = int(tempGrans)

                      if not tempGrans == index: # To break in case something is wrong wth indices
                          print 'Index not correct'
                          break

                      # Retreiving the next segment and finding direction.
                      minusTest = omr.getAttribute('childList{%i}.minus.href' % (index))
                      if minusTest != None:
                          minus = True
                          tempGransID = minusTest
                      else:
                          minus = False
                          tempGransID = omr.getAttribute('childList{%i}.plus.href' % (index))

                      # Building line
                      # This part is for the first "Gräns" either in the outer (index == 0) polygon or
                      # a hole (innerIndex >= 1)
                      if firstLine:
                          partOne = gransFinder(tempGransID, self.grans)
                          polygonBoundary = initialBoundaryLine(partOne)
                          firstLine = False
                          if minus:
                              polygonBoundary.reverse()


                      # From the second "gräns" in the list.
                      else:
                          polygonBoundaryParts = gransFinder(tempGransID, self.grans)

                          geo = polygonBoundaryParts.getGeometry()

                          nbrLines = geo.numParts()

                          tmpLine = geo.getPartAt(0)

                          if type(tmpLine) == fmeobjects.FMEArc:
                              tmpLine = tmpLine.getAsLine()

                          #Iterating over the of the parts in the FMEPath object
                          for tp in xrange(1,nbrLines):

                              tpl = geo.getPartAt(tp)

                              if type(tpl) == fmeobjects.FMEArc:
                                  tpl = tpl.getAsLine()

                              tmpLine.appendLine(tpl)

                          if minus:
                              tmpLine.reverse()

                          polygonBoundary.appendLine(tmpLine)

                      # True if a closed polygon is found.
                      if polygonBoundary.isClosed(False): # False => not considering 3D
                          firstLine = True # Next will be first line of an inner polygon (if existing)
                          innerIndex += 1 # Counting inner polygons
                          boundaryList.append(polygonBoundary) # Appending current polygon to list
                          polygonBoundary = None

                      index += 1

                  # Final part: Creating the polygons incl. holes if present
                  # Creating a polygon with the outer boundary by popping it from the list of ploygons
                  if boundaryList:
                      outerPoly = fmeobjects.FMEDonut(boundaryList.pop(0))
                      # Iterating over all inner polygons that were found (the ouoter is already removed above)
                      for omrPoly in boundaryList:
                          innerPoly = fmeobjects.FMEDonut(omrPoly)
                          outerPoly.addInnerBoundaryCurve(omrPoly)

                      omr.setGeometry(outerPoly)

                      self.pyoutput(omr)
    -> FeatureMerger_2 [REQUESTOR]
PythonCaller_Byggnadshojd_Input (input)
    -> PythonCaller_Byggnadshojd
Note: Finds byggnadshöjd / (Other heights not considered)
PythonCaller_Byggnadshojd
    PYTHONSYMBOL = processFeature
    PYTHONSOURCE:
      import fme
      import fmeobjects

      # Template Function interface:
      # When using this function, make sure its name is set as the value of
      # the 'Class or Function to Process Features' transformer parameter
      def processFeature(feature):

          if feature.getAttribute('bestammelsetyp')  == 'DP_KM_Eg_Omfatt_Byggnadshojd':
              byHojd = feature.getAttribute('beteckning')
              byHojd = byHojd.replace(',', '.')
              byHojd = float(byHojd)
              feature.setAttribute('byggnadshojd', byHojd)
    NEW_ATTRIBUTES = byggnadshojd
    -> FeatureMerger_Egenskap [SUPPLIER]
    -> GeometryFilter
GeometryFilter
    GEOM_PORT_NAMES = Point
    BREAK_AGG = No
    POINT -> PointOnAreaOverlayer [POINT]
    <UNFILTERED> -> GeometryFilter_2
Note: Unfiltered, regulations with link, no geometry.
GeometryFilter_2
    GEOM_PORT_NAMES = Line Arc Null
    BREAK_AGG = No
    NULL -> FeatureMerger_4 [SUPPLIER]
FeatureMerger_Anvandning_Supplier (input)
    -> FeatureMerger_Anvandning [SUPPLIER]
FeatureMerger_Requestor (input)
    -> FeatureMerger [REQUESTOR]
FeatureMerger_Supplier (input)
    -> FeatureMerger [SUPPLIER]
Note: Needs xml_id from the / XML-reader to join with lines.
FeatureMerger
    REJECT_NULL_MISSING_KEYS = No
    PROCESS_DUPS = No
    ATTR_CONFLICT_RES = Use Requestor
    MERGE_TYPE = Attributes Only
    JOIN_KEYS = @Value(gml_id) @Value(DP_Omrade.id) AUTO
    SUPPLIERS_FIRST = No
    IGNORE_NULLS = No
    ATTR_ACCUM_MODE = Merge Supplier
    MERGED -> AttributeKeeper
AttributeKeeper
    KEEP_ATTRS = xml_id,gml_id,xml_fragment,DP_Omrade.id,gml_parent_id
    -> AttributeCreator
AttributeCreator
    ATTR_TABLE = SET_TO ID_join = #@Value(DP_Omrade.id)
    -> FeatureMerger_Egenskap [REQUESTOR]
AttributeRemover
    REMOVE_ATTRS = minus,plus
    -> FeatureMerger_2 [SUPPLIER]
Note: Adding Geometries to bestämmelser
FeatureMerger_2
    REJECT_NULL_MISSING_KEYS = No
    PROCESS_DUPS = No
    ATTR_CONFLICT_RES = Use Requestor
    MERGE_TYPE = Attributes and Geometry
    JOIN_KEYS = @Value(xml_parent_id) @Value(xml_id) AUTO
    SUPPLIERS_FIRST = No
    IGNORE_NULLS = No
    ATTR_ACCUM_MODE = Merge Supplier
    MERGED -> AttributeRemover_2
    MERGED -> FeatureMerger_3 [REQUESTOR]
AttributeRemover_2
    REMOVE_ATTRS = xml_id,gml_id,xml_parent_child_pos,ID_join,plus.href,xml_matched_element,plus,minus.href,linje
    LIST_ATTRS = childList{}
    -> PointOnAreaOverlayer [AREA]
Note: NB!!!!!!!!!!!!!!!!!!!!!!!! / Swap ports Merged and / UnmergedRequestor if using / areas allowed to build
Note: Merging attributes from / areas allowed to build.
FeatureMerger_3
    REJECT_NULL_MISSING_KEYS = No
    PROCESS_DUPS = No
    ATTR_CONFLICT_RES = Use Requestor
    MERGE_TYPE = Attributes Only
    JOIN_KEYS = @Value(DP_Omrade.id) @Value(DP_Omrade.id) AUTO
    SUPPLIERS_FIRST = No
    IGNORE_NULLS = No
    ATTR_ACCUM_MODE = Merge Supplier
    MERGED -> FeatureMerger_4 [REQUESTOR]
Note: Merging with bestämmelser without geometry. / Areas not allowed to build (prickad mark) and / only "komplementbyggnad (korsmark)
FeatureMerger_4
    REJECT_NULL_MISSING_KEYS = No
    PROCESS_DUPS = Yes
    ATTR_CONFLICT_RES = Use Requestor
    MERGE_TYPE = Attributes and Geometry
    JOIN_KEYS = @Value(omrade.xlink_href) @Value(omrade.xlink_href) AUTO
    SUPPLIERS_FIRST = No
    GEOM_TYPE = Build Polygons
    IGNORE_NULLS = No
    CONNECT_Z_MODE = First Wins
    ATTR_ACCUM_MODE = Merge Supplier
    MERGED -> TestFilter_2
    UNMERGED_REQUESTOR -> TestFilter
    <REJECTED> -> FeatureMerger_4__Rejected_
Note: Splitting prickar mark and korsmark
TestFilter_2
    DEFAULT_VALUE = <UNFILTERED>
    TEST_LIST = BOOL_OP,OR,COMPOSITE_TEST,<Unused>,TEST_CLAUSE,"TEST @Value(bestammelsetyp) CONTAINS Prick",prickMark,BOOL_OP,OR,COMPOSITE_TEST,<Unused>,TEST_CLAUSE,"TEST @Value(bestammelsetyp) CONTAINS Kors",korsMark
    prickMark -> TestFilter_2_prickMark (output)
    korsMark -> TestFilter_2_korsMark (output)
TestFilter_2_prickMark (output)
TestFilter_2_korsMark (output)
TestFilter
    DEFAULT_VALUE = <UNFILTERED>
    TEST_LIST = BOOL_OP,OR,COMPOSITE_TEST,<Unused>,TEST_CLAUSE,"TEST @Value(anvandningsslag) CONTAINS gata",Gata,BOOL_OP,OR,COMPOSITE_TEST,<Unused>,TEST_CLAUSE,"TEST @Value(anvandningsslag) CONTAINS gang",Gång,BOOL_OP,OR,COMPOSITE_TEST,<Unused>,TEST_CLAUSE,"TEST @Value(anvandningsslag) CONTAINS cykel",Cykel,BOOL_OP,OR,COMPOSITE_TEST,<Unused>,TEST_CLAUSE,"TEST @Value(beteckning) CONTAINS vatten",Vatten
    Gata -> TestFilter_Gata (output)
    Gång -> TestFilter_Gång (output)
    Cykel -> TestFilter_Cykel (output)
    Vatten -> TestFilter_Vatten (output)
    <UNFILTERED> -> TestFilter__Unfiltered_ (output)
TestFilter_Gata (output)
TestFilter_Gång (output)
TestFilter_Cykel (output)
TestFilter_Vatten (output)
TestFilter__Unfiltered_ (output)
FeatureMerger_4__Rejected_: Inspector

Bookmark: Connects bestämmelser to områden
FeatureMerger_Egenskap
    REJECT_NULL_MISSING_KEYS = No
    PROCESS_DUPS = Yes
    ATTR_CONFLICT_RES = Use Requestor
    MERGE_TYPE = Attributes Only
    JOIN_KEYS = @Value(ID_join) @Value(omrade.xlink_href) AUTO
    LIST_ATTRS_TO_INCLUDE = beteckning ursprunglig uuid
    SUPPLIERS_FIRST = No
    GEOM_TYPE = Build Polygons
    LIST_NAME = EgenskapList
    IGNORE_NULLS = No
    CONNECT_Z_MODE = First Wins
    ATTR_ACCUM_MODE = Merge Supplier
    MERGED -> FeatureMerger_Anvandning [REQUESTOR]
    UNMERGED_REQUESTOR -> FeatureMerger_Anvandning [REQUESTOR]
FeatureMerger_Anvandning
    REJECT_NULL_MISSING_KEYS = No
    PROCESS_DUPS = Yes
    ATTR_CONFLICT_RES = Use Requestor
    MERGE_TYPE = Attributes Only
    JOIN_KEYS = @Value(ID_join) @Value(omrade.xlink_href) AUTO
    LIST_ATTRS_TO_INCLUDE = beteckning ursprunglig uuid
    SUPPLIERS_FIRST = No
    GEOM_TYPE = Build Polygons
    LIST_NAME = AnvandningList_beteckning
    IGNORE_NULLS = No
    CONNECT_Z_MODE = First Wins
    ATTR_ACCUM_MODE = Merge Supplier
    MERGED -> AttributeRemover
    UNMERGED_REQUESTOR -> AttributeRemover

Bookmark: Finds area where buildings are permitted
Note: To get egenskaper from points
PointOnAreaOverlayer
    CANDIDATE_LIST_ATTRS_TO_INCLUDE = beteckning ursprunglig variabel{}.DP_VarArtal.namn variabel{}.DP_VarArtal.varde variabel{}.DP_VarDatum.namn variabel{}.DP_VarDatum.varde variabel{}.DP_VarDecimaltal.namn variabel{}.DP_VarDecimaltal.varde variabel{}.DP_VarHeltal.namn variabel{}.DP_VarHeltal.varde variabel{}.DP_VarKod.namn variabel{}.DP_VarKod.varde variabel{}.DP_VarLinje.namn variabel{}.DP_VarLinje.varde variabel{}.DP_VarPunkt.namn variabel{}.DP_VarPunkt.varde variabel{}.DP_VarText.namn variabel{}.DP_VarText.varde variabel{}.owns
    POLYS_FIRST = NO
    ATTR_CONFLICT_RES = Use Original
    CANDIDATE_LIST_ATTRS_TO_INCLUDE_MODE = Selected Attributes
    OV_ATTR = _overlaps
    CANDIDATE_LIST_NAME = egenskap
    ATTR_ACCUM_MODE = Merge Incoming
    DEAGGREGATE_INPUT = Yes
    AREA -> PythonCaller_Nockhojd
Note: Finds max nockhöjd / (Other heights not considered)
PythonCaller_Nockhojd
    PYTHONSYMBOL = processFeature
    PYTHONSOURCE:
      import fme
      import fmeobjects
      # Template Function interface:
      # When using this function, make sure its name is set as the value of
      # the 'Class or Function to Process Features' transformer parameter
      def processFeature(feature):
          testString = 'gsta nockh'
          i = 0
          item = feature.getAttribute('egenskap{%i}.ursprunglig' % (i))
          maxNock = None

          while item:
              if testString in item:
                  maxNock = feature.getAttribute('egenskap{%i}.beteckning' % (i))
                  break
              i += 1
              item = feature.getAttribute('egenskap{%i}.ursprunglig' % (i))
          if maxNock:
              maxNock = maxNock.replace(",",".")
              maxNock = float(maxNock)
              feature.setAttribute('max_nock', maxNock)
    NEW_ATTRIBUTES = max_nock
    -> PythonCaller_Takvinkel
Note: Finds min and max takvinkel
PythonCaller_Takvinkel
    PYTHONSYMBOL = processFeature
    PYTHONSOURCE:
      import fme
      import fmeobjects
      # Template Function interface:
      # When using this function, make sure its name is set as the value of
      # the 'Class or Function to Process Features' transformer parameter
      def processFeature(feature):
          testString_1 = 'gsta taklutning'
          teststring_2 = 'taklutning i grader'
          i = 0
          item = feature.getAttribute('egenskap{%i}.ursprunglig' % (i))
          maxTakVinkel = False
          minTakVinkel = False

          while item:
              if testString_1 in item:
                  maxTakVinkel = feature.getAttribute('egenskap{%i}.beteckning' % (i))
                  break
              elif teststring_2 in item:
                  varIndex = 0
                  varItem = feature.getAttribute('egenskap{%i}.variabel{%i}.DP_VarDecimaltal.namn' % (i, varIndex))
                  while varItem:
                      if 'minvinkel' in varItem:
                          minTakVinkel = feature.getAttribute('egenskap{%i}.variabel{%i}.DP_VarDecimaltal.varde' % (i, varIndex))
                      elif 'maxvinkel' in varItem:
                          maxTakVinkel = feature.getAttribute('egenskap{%i}.variabel{%i}.DP_VarDecimaltal.varde' % (i, varIndex))
                      varIndex += 1
                      varItem = feature.getAttribute('egenskap{%i}.variabel{%i}.DP_VarDecimaltal.namn' % (i, varIndex))
              i += 1
              item = feature.getAttribute('egenskap{%i}.ursprunglig' % (i))

          if maxTakVinkel:
              #maxTakVinkel = maxTakVinkel.replace(",",".")
              #maxTakVinkel = float(maxTakVinkel)
              feature.setAttribute('max_takvinkel', maxTakVinkel)
          if minTakVinkel:
              feature.setAttribute('min_takvinkel', minTakVinkel)
    NEW_ATTRIBUTES = max_takvinkel min_takvinkel
    -> AttributeKeeper_2
AttributeKeeper_2
    KEEP_ATTRS = max_nock,DP_Omrade.id,max_takvinkel,byggnadshojd,min_takvinkel
    -> FeatureMerger_3 [SUPPLIER]

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

Input (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    GQUERY:
      for $geom in //geometry
      where $geom/count(parent::geometry) = 0
      return number($geom/@fme_id)
    SETTYPE_PARAM = Traits From Attributes
    SRC_ATTRS = citygml_lod_name
    REMOVE_ATTRIBUTE = No
    OVERWRITE_CHOICE = Yes
    SET -> Output (output)
Output (output)

FME custom transformer IntersectionLineCreatetor

SurfaceFootprintReplacer_Input (input)
    -> SurfaceFootprintReplacer
Note: To find footprint for centre point and extent of area
SurfaceFootprintReplacer
    LIGHT_X = 0
    OFFSET_Z = 0
    LIGHT_Y = 0
    LIGHT_Z = 1
    SHADOW_MODE = Overhead Shadow
    FOOTPRINT -> Dissolver
Dissolver
    ACCUM_INPUT_ATTRS = Drop Incoming Attributes
    NO_OVRLP = No
    CONNECT_Z_MODE = Ignore
    DEAGGREGATE_INPUT = Yes
    AREA -> AreaCalculator
Note: Assuming that the largest area is the main footprint
AreaCalculator
    AREA_ATTR = _area
    AREA_TYPE = Plane Area
    MULT = 1
    -> Sorter
Sorter
    SORT_PARM = _area NUMERIC DESCENDING
    SORTED -> Counter
Counter
    SCOPE = Global
    CNT_ATTR = _count
    DOMAIN = counter
    START = 0
    -> Tester
Tester
    TEST_CLAUSE = TEST @Value(_count) = 0
    BOOL_OP = OR
    TEST_MODE = Automatic
    PASSED -> CoordinateExtractor
Note: To find max x value of the footprint
CoordinateExtractor
    MODE = All Coordinates
    LIST_NAME = _indices
    -> ListRangeExtractor
ListRangeExtractor
    MAX = maxX
    MIN = minX
    SRC_LIST = _indices{}.x
    -> AttributeRemover
Note: Removing list of coordinates
Note: Here a centre point inside the footprint is found and a line starting / from the centre point is used to find / one outer wall via intersection
AttributeRemover
    LIST_ATTRS = _indices{} _indices{}.x _indices{}.y _indices{}.z
    -> CenterPointReplacer
Note: To get only one line. / NB! what is best centre point? / Now "inside" is selected to force it to be inside the footprint
CenterPointReplacer
    MODE = Inside Point
    POINT -> CoordinateExtractor_2
CoordinateExtractor_2
    MODE = All Coordinates
    LIST_NAME = _indices
    -> Extruder
Extruder
    EXTRUSION_Y = 0.0
    EXTRUSION_X = @Value(maxX) - @Value(minX)
    EXTRUSION_Z = 0.0
    DIRECTION = Specified
    EXTRUDED -> AttributeCreator
Note: To identify line after intersection
AttributeCreator
    ATTR_TABLE = SET_TO IntersectLine = line
    -> AttributeKeeper
AttributeKeeper
    KEEP_ATTRS = IntersectLine
    -> 2DForcer_2
2DForcer_2
    2D -> 2DForcer_2_2D (output)
2DForcer_2_2D (output)

FME custom transformer BuildingHeightCheckerCurrent

mainWallFinder_2 (input)
    -> 2DForcer_3
mainWallFinder (input)
    -> HullAccumulator
DevelopmentPlan_Input (input)
    -> Junction_6
Note: Only to visualilse the 16 / elevation points.
FeatureColorSetter [off]
    COLOR = 0.666667,0,0
    MODE = Fixed
    FILL_COLOR = 0.666667,0,0
    COLORED -> FeatureColorSetter_Colored
FeatureColorSetter_Colored: Inspector [off]

Bookmark: Creating the horisontal plane representing mean ground elevation.
2DForcer_3
    2D -> BoundsExtractor
    2D -> HullAccumulator_2
AttributeKeeper_4
    KEEP_ATTRS = _angle,pointElevation,wallHeightOLD,_closest_candidate_x,_candidate_angle,_distance,_closest_base_x,wallHeightNEW,_closest_candidate_y,_closest_base_y,wallOrderID,zOffset
    -> Aggregator_2
    -> PythonCaller_GroundPointLifter
Note: Calculates mean ground elevation
PythonCaller_GroundPointLifter
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.pointList = []
              self.totElevation = 0
              self.elevOK = None

          def input(self,feature): # This function is called every time a feature is added
              if not feature.hasGeometry():
                  self.elevOK = feature.getAttribute('elevOK')
              else:
                  self.pointList.append(feature)
                  self.totElevation += feature.getAttribute('pointElevation')

          def close(self):
              if not self.elevOK:
                  print 'Elevation points are not including the highest and lowest points'
              else:
                  # Mean elevation of the ground around the building
                  meanElevation = self.totElevation*1.0/len(self.pointList)
                  # Iterating over all points and assigning z-value
                  for tempPoint in self.pointList:
                      tp = tempPoint.getGeometry()
                      tp.setZ(tempPoint.getAttribute('pointElevation'))
                      tempPoint.setGeometry(tp)
                      tempPoint.setAttribute('meanElevation', meanElevation)

                      self.pyoutput(tempPoint)
    NEW_ATTRIBUTES = meanElevation
    -> PointOnAreaOverlayer_2 [POINT]
    -> FeatureColorSetter
PointOnAreaOverlayer_2
    POLYS_FIRST = No
    ATTR_CONFLICT_RES = Use Original
    CANDIDATE_LIST_ATTRS_TO_INCLUDE_MODE = Selected Attributes
    OV_ATTR = _overlaps
    ATTR_ACCUM_MODE = Merge Incoming
    DEAGGREGATE_INPUT = Yes
    AREA -> Offsetter_3
Note: Lifting the plane to the mean ground level.
Offsetter_3
    ZOFF = @Value(meanElevation)
    MODE = Cartesian Coordinate
    YOFF = 0
    XOFF = 0
    OFFSET -> FeatureColorSetter_2
    <REJECTED> -> Offsetter_3__Rejected_
FeatureColorSetter_2
    COLOR = 0.666667,0,0
    MODE = Fixed
    FILL_COLOR = 0.666667,0,0
    COLORED -> PythonCaller_heightChecker
Offsetter_3__Rejected_: Inspector

Bookmark: Finding wall lenghts
  Calculates lenght of each side of the buidling
BoundsExtractor
    YMIN = _ymin
    ZMIN = _zmin
    YMAX = _ymax
    ZMAX = _zmax
    XMIN = _xmin
    XMAX = _xmax
    -> PythonCaller_EndPointFinder
PythonCaller_EndPointFinder
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.lineList = []

          def input(self,feature): # This function is called every time a feature is added
              self.lineList.append(feature)

          def close(self):

              # Iterating over all walls to keep endpoints only
              for wallLine in self.lineList:

                  xMax = wallLine.getAttribute('_xmax')
                  xMin = wallLine.getAttribute('_xmin')
                  yMax = wallLine.getAttribute('_ymax')
                  yMin = wallLine.getAttribute('_ymin')
                  inLine = wallLine.getGeometry() # We get the geometry as a face

                  # Have not found a way of checking what geometry type the area is
                  # so using try to see if it is donut och polygon
                  try:
                      # Only outer boundary is interesting (i.e. openings not relevant)
                      pl = inLine.getOuterBoundaryAsCurve()
                  except:
                      pl = inLine.getBoundaryAsCurve()

                  pointList = pl.getPoints()

                  candidatePoints = []

                  # Looping over all points in the list keeping only those that include one
                  # boundary coordinate as candidates. Other points cannot be endpoints.
                  for tempPoint in pointList:
                      tempXYZ = tempPoint.getXYZ()
                      if xMax == tempXYZ[0] or xMin == tempXYZ[0] or yMax == tempXYZ[1] or yMin == tempXYZ[1]: # No need to check ground level points

                          candidatePoints.append(tempPoint)


                  currentLen = 0

                  for startIndex in xrange(len(candidatePoints)):
                      tempStart = candidatePoints[startIndex]
                      for endIndex in xrange(len(candidatePoints)):
                          if not startIndex == endIndex:
                              tempend = candidatePoints[1]
                              tempLen = sqrt((tempStart.getXYZ()[0]-tempend.getXYZ()[0])**2 + (tempStart.getXYZ()[1]-tempend.getXYZ()[1])**2)
                              if tempLen > currentLen:
                                  currentLen = tempLen
                                  currentStartIndex = startIndex
                                  currentEndIndex = endIndex

                  newLine = fmeobjects.FMELine([candidatePoints[currentStartIndex].getXYZ(), candidatePoints[currentEndIndex].getXYZ()])

                  wallLine.setGeometry(newLine)

                  self.pyoutput(wallLine)
    -> LengthCalculator
LengthCalculator
    LEN_ATTR = _length
    DIM = 2
    MULT = 1
    -> PythonCaller_NumberOfLineSplits

Bookmark: Creating 16 points along the building walls used to derive mean ground elevation
Note: Calculates how many points to include for / each side of the building.
PythonCaller_NumberOfLineSplits
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.lineList = []
              self.totLen = 0
              self.nbrPoints = 16.0 # Number of points to calculate mean ground elevation

          def input(self,feature): # This function is called every time a feature is added
              self.lineList.append(feature)
              self.totLen += feature.getAttribute('_length')

          def close(self):

              lineFractions = []
              nbrPoints = []

              for wallLine in self.lineList:
                  lineFractions.append(wallLine.getAttribute('_length')/self.totLen)
                  # Number of line segments to split into
                  np = round(wallLine.getAttribute('_length')/self.totLen*self.nbrPoints)
                  nbrPoints.append(np)

                  # Creates points with a distance of half the DEM resolution to chekc that the highest and lowest
                  # elevation point is included among the points used to derived mean ground elevation.
                  npDense = round(wallLine.getAttribute('_length')/float(FME_MacroValues['DEM_resolution'])*2.0)

                  wallLine.setAttribute('nbrLines', np)
                  wallLine.setAttribute('nbrLinesDense', npDense)

                  self.pyoutput(wallLine)

              if sum(nbrPoints) != self.nbrPoints:
                  print 'WARNING!!!, number of line segments is not {}'.formatt(self.nbrPoints)
    NEW_ATTRIBUTES = nbrLines nbrLinesDense
    -> IterativeSnipper
    -> IterativeSnipper_2

Bookmark: Walls -> points
  Splits the walls of the building into lines (16 to calculate mean ground elevation) and replaces the lines with a point at the startpoint of the line. Start is used to get points at the corners of the buidling.
IterativeSnipper
    SNIPMODE = ToNumber
    SnipLength = @Value(nbrLines)
    -> LengthCalculator_2
LengthCalculator_2
    LEN_ATTR = _length
    DIM = 2
    MULT = 1
    -> Tester_2
Tester_2
    TEST_DESCRIPTION = ""
    TEST_CLAUSE = TEST @Value(_length) > 0.1
    BOOL_OP = OR
    TEST_MODE = Automatic
    PASSED -> CoordinateExtractor_3
CoordinateExtractor_3
    Y_ATTR = _yPoint
    IND = 0
    Z_ATTR = _zPoint
    X_ATTR = _xPoint
    MODE = Specify Coordinate
    -> PythonCaller_PointCreator
Note: Replaces the line geometries with / a point at the start point of the line.
PythonCaller_PointCreator
    PYTHONSYMBOL = FeatureProcessor
    PYTHONSOURCE:
      import fme
      import fmeobjects

      # Template Class Interface:
      # When using this class, make sure its name is set as the value of
      # the 'Class or Function to Process Features' transformer parameter
      class FeatureProcessor(object):
          def __init__(self):
              self.lineList = []

          def input(self,feature):
              self.lineList.append(feature)

          def close(self):
              for l in self.lineList:
                  # Reading coords of first point of the line
                  x = l.getAttribute('_xPoint')
                  y = l.getAttribute('_yPoint')
                  z = l.getAttribute('_zPoint')

                  newPoint = fmeobjects.FMEPoint(x, y, z)
                  l.setGeometry(newPoint)
                  self.pyoutput(l)
    -> NeighborFinder [BASE]

Bookmark: Finding max and min elevation for the dense points.
  Finding max and min elevation for the dense points (distance = halv DEM resolution) to confirm that the highest and lowest points in teh DEM around the buidling are included among the 16 points used to derive mean ground elevation.
IterativeSnipper_2
    SNIPMODE = ToNumber
    SnipLength = @Value(nbrLinesDense)
    -> LengthCalculator_3
LengthCalculator_3
    LEN_ATTR = _length
    DIM = 2
    MULT = 1
    -> Tester_3
Tester_3
    TEST_DESCRIPTION = ""
    TEST_CLAUSE = TEST @Value(_length) > 0.1
    BOOL_OP = OR
    TEST_MODE = Automatic
    PASSED -> CenterPointReplacer_3
CenterPointReplacer_3
    MODE = Center Point
    POINT -> NeighborFinder_2 [BASE]
from_DEM (input)
    -> CoordinateExtractor_2
CoordinateExtractor_2
    Y_ATTR = _y
    IND = 0
    Z_ATTR = _z
    X_ATTR = _x
    MODE = Specify Coordinate
    -> AttributeCreator_4
AttributeCreator_4
    ATTR_TABLE = SET_TO pointElevation = @Value(_z)
    -> AttributeKeeper_5
AttributeKeeper_5
    KEEP_ATTRS = pointElevation
    -> NeighborFinder_2 [CANDIDATE]
NeighborFinder_2
    MODE = Bases and Candidates
    MEASURES_FROM_CANDIDATE = Yes
    ATTR_CONFLICT_RES = Use Base
    INSERT_VERTEX = No
    MEASURE_TYPE = Continuous
    TREAT_POLYGON_AS = Lines
    K = 1
    CANDIDATES_FIRST = No
    ATTR_ACCUM_MODE = Merge Candidate
    MATCHED -> AttributeKeeper_6
    <REJECTED> -> NeighborFinder__Rejected__2
AttributeKeeper_6
    KEEP_ATTRS = _angle,pointElevation,wallHeightOLD,_closest_candidate_x,_candidate_angle,_distance,_closest_base_x,wallHeightNEW,_closest_candidate_y,_closest_base_y,wallOrderID,zOffset
    -> Aggregator_3
NeighborFinder__Rejected__2: Inspector

Bookmark: Plane for height visualisation
  Creating a plane extending with the buffer amount outside teh building. Used for visualisation of mean ground surface later.
HullAccumulator_2
    HULLTYPE_PARAM = Convex ()
    3DMODE_PARAM = 2D
    HULL -> Generalizer
Generalizer
    ALG_TEXT = Douglas (Generalize)
    TOLERANCE = 1
    PRESERVE = No
    -> Bufferer
Bufferer
    CAP_STYLE = None
    ANGLE = 22.5
    MITER_LIMIT = 3
    CORNER_STYLE = Miter
    OFFSET = 3
    BUFFERED -> PointOnAreaOverlayer_2 [AREA]

Bookmark: To find in which area the building is located
HullAccumulator
    HULLTYPE_PARAM = Convex ()
    3DMODE_PARAM = 2D
    HULL -> Clipper_3 [CLIPPER]
Note: Detailed plan areas
Junction_6
    -> Clipper_3 [CLIPPEE]
Clipper_3
    BOUNDARY_CASES = Treat as Inside
    LINES_AS_SEGMENTS = No
    CLIPPED_ATTR = _clipped
    ATTR_CONFLICT_RES = Use Clippee
    MISSING_VAL_MODE = Compute
    MEASURE_TYPE = Continuous
    CLIP_TYPE = Multiple Clippers
    PRESERVE_CLIPPEE_EXTENTS = No
    DEFAULT_VAL = 0
    VAL_SOURCE = Clippee Only
    CREATE_AGGREGATES = Yes
    CONNECT_Z_MODE = First Wins
    ATTR_ACCUM_MODE = Merge Clipper
    INSIDE -> PythonCaller_heightChecker

Bookmark: Checking min and max elevation
  Checking that the highest and lowest points are included with the 16 points used to find mean ground elevation.
Aggregator_3
    ORDERED = No
    MODE = Geometry - Assemble One Level
    ACCUM_ATTRS_NAME = Merge Incoming Attributes
    SEP = ,
    AGGREGATE_TYPE = Homogeneous Collection (If Possible)
    LIST_ATTRS_TO_INCLUDE = pointElevation
    LIST_NAME = pointElevationList
    AGGREGATE -> ListRangeExtractor_2
ListRangeExtractor_2
    MAX = _maxElevDense
    MIN = _minElevDense
    SRC_LIST = pointElevationList{}.pointElevation
    -> PythonCaller_GroundPointLifter_2
Aggregator_2
    ORDERED = No
    MODE = Geometry - Assemble One Level
    ACCUM_ATTRS_NAME = Merge Incoming Attributes
    SEP = ,
    AGGREGATE_TYPE = Homogeneous Collection (If Possible)
    LIST_ATTRS_TO_INCLUDE = pointElevation
    LIST_NAME = pointElevationList
    AGGREGATE -> ListRangeExtractor
ListRangeExtractor
    MAX = _maxElev
    MIN = _minElev
    SRC_LIST = pointElevationList{}.pointElevation
    -> PythonCaller_GroundPointLifter_2
Note: Checks that the min and max / elevations are included with / the 16 points.
PythonCaller_GroundPointLifter_2
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.pointList = []
              self.pointListDense = []


          def input(self,feature): # This function is called every time a feature is added
              if feature.getAttribute('_minElevDense'):
                  self.pointListDense.append(feature)
              elif feature.getAttribute('_minElev'):
                  self.pointList.append(feature)

          def close(self):
              # Checking that min and max elevations are included in the 16 points
              minElevDiff = float(self.pointList[0].getAttribute('_minElev')) - float(self.pointListDense[0].getAttribute('_minElevDense'))
              maxElevDiff = float(self.pointList[0].getAttribute('_maxElev')) - float(self.pointListDense[0].getAttribute('_maxElevDense'))

              # Creating a new feature with the attribute elevOK with the value True if highest
              # and lowest points of teh building are included in the 16 points.
              nf = fmeobjects.FMEFeature()
              if abs(minElevDiff) < 0.01 and abs(maxElevDiff) < 0.01:
                  nf.setAttribute('elevOK', True)
              else:
                  nf.setAttribute('elevOK', False)

              self.pyoutput(nf)
    NEW_ATTRIBUTES = elevOK
    -> PythonCaller_GroundPointLifter

Bookmark: Getting elevation for the 16 points along the buildiing walls.
from_DEM_2 (input)
    -> CoordinateExtractor
CoordinateExtractor
    Y_ATTR = _y
    IND = 0
    Z_ATTR = _z
    X_ATTR = _x
    MODE = Specify Coordinate
    -> AttributeCreator_3
AttributeCreator_3
    ATTR_TABLE = SET_TO pointElevation = @Value(_z)
    -> AttributeKeeper_3
AttributeKeeper_3
    KEEP_ATTRS = pointElevation
    -> NeighborFinder [CANDIDATE]
NeighborFinder
    MODE = Bases and Candidates
    MEASURES_FROM_CANDIDATE = Yes
    ATTR_CONFLICT_RES = Use Base
    INSERT_VERTEX = No
    MEASURE_TYPE = Continuous
    TREAT_POLYGON_AS = Lines
    K = 1
    CANDIDATES_FIRST = No
    ATTR_ACCUM_MODE = Merge Candidate
    MATCHED -> AttributeKeeper_4
    <REJECTED> -> NeighborFinder__Rejected_
NeighborFinder__Rejected_: Inspector

Bookmark: Checking if the building heigth is allowed according to the development plan.
  Checks the building height against the development plan and displays the ground elevation plane. 
  If the building is too high, a horisontal plane representing max allowed building height is visualised.
Note: Checks if building height is allowed. / Adds the attribute heightOK with the / value True or False.
PythonCaller_heightChecker
    PYTHONSYMBOL = FeatureProcessor
    PYTHONSOURCE:
      import fme
      import fmeobjects
      from math import sqrt

      # Template Class Interface:
      # When using this class, make sure its name is set as the value of
      # the 'Class or Function to Process Features' transformer parameter
      class FeatureProcessor(object):
          def __init__(self):
              self.byggnadsHojd = None
              self.by = None
              self.maxByggnadsHojd = None

          def input(self,feature): # This function is called every time a feature is added
              if feature.getAttribute('gml_parent_property') == 'egenskapsbestammelse':
                  self.maxByggnadsHojd = float(feature.getAttribute('byggnadshojd'))
              elif feature.getAttribute('wallHeightOLD'):
                  self.byggnadsHojd = float(feature.getAttribute('wallHeightOLD'))
                  self.by = feature


          def close(self):

              # Checing if the building is lower than the allowed height with the
              # allowed toleracne of 10 cm.
              if self.byggnadsHojd - self.maxByggnadsHojd < 0.1:
                  self.by.setAttribute('heightOK', True)
              else:
                  self.by.setAttribute('heightOK', False)
                  nf = self.by.clone()
                  geo = nf.getGeometry()
                  nl = geo.getBoundaryAsCurve()
                  np = nl.getPoints()

                  # Horisontal surface so we can take z from any point
                  newZ = np[0].getXYZ()[2] + self.maxByggnadsHojd
                  # new pointlist with coordinates lifted to max building height
                  [p.setZ(newZ) for p in np]
                  liftedXYZ = [p.getXYZ() for p in np]
                  liftedLine = fmeobjects.FMELine(liftedXYZ)
                  liftedPoly = fmeobjects.FMEPolygon(liftedLine)
                  nf.setGeometry(liftedPoly)
                  nf.setAttribute('maxHeight', 'True')
                  self.pyoutput(nf)

              self.pyoutput(self.by)
    NEW_ATTRIBUTES = heightOK maxHeight
    -> TestFilter_6
TestFilter_6
    DEFAULT_VALUE = <UNFILTERED>
    TEST_LIST = BOOL_OP,OR,COMPOSITE_TEST,<Unused>,TEST_CLAUSE,"TEST @Value(maxHeight) = True",maxHeight
    maxHeight -> maxHeight_if_too_high (output)
    <UNFILTERED> -> groundElevation (output)
maxHeight_if_too_high (output)
groundElevation (output)

FME custom transformer StoreyIndexFinder

Parameters:
- storeyIndex = 1   # Floor index
- IFC_UNIQUE_ID = @Value(ifc_unique_id)   # Ifc Unique Id

Note: Connect to UUID creator for the walls
AttributeCreator_StoreyList_Input (input)
    -> AttributeCreator_StoreyList
AttributeCreator_StoreyList
    ATTR_TABLE = SET_TO storeyListIndex
    -> PythonCaller_2
Note: Connect to ListElementCounter / belonging to IfcBuildingStorey
PythonCaller_2_Input (input)
    -> Aggregator_2
Aggregator_2
    ORDERED = No
    MODE = Attributes Only
    ACCUM_ATTRS_NAME = Merge Incoming Attributes
    SEP = ,
    CONCAT_ATTRS = ifc_unique_id
    LIST_ATTRS_TO_INCLUDE = ifc_unique_id
    LIST_NAME = buildingStoreysID
    AGGREGATE -> ListElementCounter
ListElementCounter
    CNT_ATTR = nbrStoreys
    LIST_NAME = buildingStoreysID{}
    -> PythonCaller_2
PythonCaller_2
    PYTHONSYMBOL = FeatureProcessor
    PYTHONSOURCE:
      import fme
      import fmeobjects
      # Template Function interface:
      # When using this function, make sure its name is set as the value of
      # the 'Class or Function to Process Features' transformer parameter
      def processFeature(feature):
          pass


      def listFinder(f): # f - the list with all features
          pos = 0 # Index in list
          while pos < len(f):
              attList = f[pos].getAllAttributeNames() # get all feature attributes
              for att in attList:
                  if 'buildingStoreysID' in att:
                      return f[pos].getAttribute('buildingStoreysID{}.ifc_unique_id')
              pos += 1
          return None

      def storeyIndexFinder(fe,storeyList):
          # Returns the index in the storey list of current feature
          parentID = fe.getAttribute('ifc_parent_unique_id')
          pos = 0
          while pos < len(storeyList):
              if storeyList[pos] == parentID:
                  return pos
              else:
                  pass # Do nothing
              pos += 1

      # Template Class Interface:
      # When using this class, make sure its name is set as the value of
      # the 'Class or Function to Process Features' transformer parameter
      class FeatureProcessor(object):
          def __init__(self):
              self.featureList = []
              self.logger = fmeobjects.FMELogFile()
              # logger.logMessageString('message')

          def input(self,feature): # This function is called every time a feature is added
              self.featureList.append(feature)

          def close(self):
              li = listFinder(self.featureList) # Return a list with storey id
              for f in self.featureList:
                  currIndex = storeyIndexFinder(f, li) # Check feature parent_id against list with storey id
                  f.setAttribute("storeyListIndex", currIndex)
                  self.pyoutput(f)
    NEW_ATTRIBUTES = storeyListIndex
    -> Tester_StoreyIndex
Note: Which storey index to include
Tester_StoreyIndex
    TEST_DESCRIPTION = ""
    TEST_CLAUSE = TEST @Value(storeyListIndex) = $(storeyIndex)
    BOOL_OP = OR
    TEST_MODE = Automatic
    PASSED -> Tester_StoreyIndex_Passed (output)
Tester_StoreyIndex_Passed (output)

FME custom transformer SurfaceNormalCalculator
This custom transformer calculates the coefficients of unit normal vector for each introduced polygon (attributes "normalX", "normalY", "normalZ"). The angle (attribute Slope) to the vertical is also derived from the direction of the surface normal vector. Values of 0 indicate perpendicular, 90 horizontal polygons. Furthermore, the 2D area is output in the attribute "signedArea2D" per polygon. Depending on the sign, a statement can be made about the orientation of the polygon. Negative values indicate polygons clockwise, positive counter-clockwise direction-oriented.
In order to obtain meaningful results, it is important to ensure that only planar polygons are initiated. All non-area features are routed unchanged through the rejected port.

INPUT (input)
    -> GeometryFilter
Note: use only closed polygons
GeometryFilter
    BREAK_AGG = No
    POINT -> Invalid (output)
    LINE -> Invalid (output)
    ARC -> Invalid (output)
    AREA -> CoordinateCounter
    ELLIPSE -> Invalid (output)
    TEXT -> Invalid (output)
    RASTER -> Invalid (output)
    SURFACE -> Invalid (output)
    SOLID -> Invalid (output)
    COLLECTION -> Invalid (output)
    NULL -> Invalid (output)
CoordinateCounter
    CNT_ATTR = _coordcount
    -> PythonCaller
PythonCaller
    PYTHONSYMBOL = calcNormal
    PYTHONSOURCE:
      import math
      import fmeobjects
      # Template Function interface:
      def calcNormal(feature):

          counter0 = 0
          coordCount = feature.numVertices() - 1

          normalX = 0
          normalY = 0
          normalZ = 0
          areaTri = 0
          area = 0
          angle = 0

          # loop through the coordinates and calculate surface normal of the triangle formed by the
          # the point, its predecessor and its successor.
          while counter0 < coordCount:

              # get test coordinate and the ones before and after
              before = (counter0 + (coordCount - 1)) % coordCount
              after = (counter0 + (coordCount + 1)) % coordCount
              coords0 = feature.getCoordinate(before)
              coords1 = feature.getCoordinate(counter0)
              coords2 = feature.getCoordinate(after)

              # calculate normal
              x1 = coords0[0]
              x2 = coords1[0]
              x3 = coords2[0]

              y1 = coords0[1]
              y2 = coords1[1]
              y3 = coords2[1]

              z1 = coords0[2]
              z2 = coords1[2]
              z3 = coords2[2]

              normalX = normalX + ((y2-y1) * (z3-z1) - (y3-y1) * (z2-z1))
              normalY = normalY + ((z2-z1) * (x3-x1) - (z3-z1) * (x2-x1))
              normalZ = normalZ + ((x2-x1) * (y3-y1) - (x3-x1) * (y2-y1))

              counter0 = counter0 + 1

              # polygon area (Gauss area formula)
              areaTri = ((y2+y3)*(x2-x3))/2
              area = area + areaTri


          # normalize vector
          length = math.sqrt(normalX**2 + normalY**2 + normalZ**2)

          if length <> 0:
              normalX = normalX / length
              normalY = normalY / length
              normalZ = normalZ / length
          else:
              normalX = 0
              normalY = 0
              normalZ = 0

          # angle
          if normalZ <>0:
              angle = math.fabs(math.atan(math.sqrt(normalX**2+normalY**2)/normalZ)*(180/3.14))
          else:
              angle = 90


          # write normal to feature
          feature.setAttribute('normalX',normalX)
          feature.setAttribute('normalY',normalY)
          feature.setAttribute('normalZ',normalZ)
          feature.setAttribute('signedArea2D',area)
          feature.setAttribute('Slope',angle)
    NEW_ATTRIBUTES = normalX normalY normalZ Slope signedArea2D
    -> AttributeRemover_3
AttributeRemover_3
    REMOVE_ATTRS = _coordcount
    -> Ok (output)
Ok (output)
Invalid (output)
