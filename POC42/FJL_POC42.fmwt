FME workspace FJL_POC42.fmwt
Title: detaljPlanReader_multiHoles_Karlstad_github_version

Parameters:
- SourceDataset_GML_5 = $(FME_MF_DIR)karlstad.xml   # Source Geography Markup Language (GML) File(s)
- SourceDataset_XML = $(FME_MF_DIR)karlstad.xml   # Source XML File(s)
- SourceDataset_XML_3 = $(FME_MF_DIR)Lotsen_by_lod1_citygml_v0.1_solid_isak_PO_storeys_function.gml   # Source XML File(s)
- XlsReport = $(FME_MF_DIR)LotsenReport.xls   # Path and name of Excel report

Readers:
- GML_1: GML from $(SourceDataset_GML_5)
- XML_1: XML from $(SourceDataset_XML)
- XML_2: XML from $(SourceDataset_XML_3)

AppearanceSetter_LOD1_building
    AMBIENT_COLOR = 0.666667,0.333333,0
    DEF_STORAGE = Create New Definitions
    DIFFUSE_COLOR = 0.666667,0.333333,0
    GQUERY:
      for $geom in //geometry
      where $geom/count(parent::geometry) = 0
      return number($geom/@fme_id)
    SET_ON_SIDE = Front and Back Sides
    SPECULAR_COLOR = 0.666667,0,0
    TEXTURE_MAPPING_TYPE_CHOICE = Surface Normal
    TEXTURE_U_OFFSET2 = 0.0
    TEXTURE_U_SCALE_FACTOR = 1.0
    TEXTURE_V_OFFSET2 = 0.0
    TEXTURE_V_SCALE_FACTOR = 1.0
    USE_EXISTING_TEXTURE_COORDINATES = No
    -> LOD1_building
LOD1_building: Inspector
FeatureColorSetter
    COLOR = 0.333333,0,0
    FILL_COLOR = 0.333333,0,0
    MODE = Fixed
    COLORED -> BuildingFootprint
BuildingFootprint: Inspector
Note: Workspace för att importera en detaljplan enligt SS 637040 och kolla bestämmelser mot en byggnad enligt föreslagen svensk profil av CityGML3. Skapat med FME 2018.1.2.0 / Polygoner för områden i detaljplanen skapas och bestämmelser kopplas till polygonerna. Workspacet hanterar inte kartografin utan ska ses som ett verktyg för att hantera bestämmelser vid kontroll av bygglov. Bestämmelser och information som gäller för hela planen kopplas inte till något område. / Framtagandet av FME skriptet är finansierat av: / Projektet Får Jag Lov koordinerat av Boverket.
Note: This workspace is released under the 3-Clause BSD License. For details, see https://opensource.org/licenses/BSD-3-Clause / Copyright (c) 2018, Lunds universitet / All rights reserved.
Note: Create list with gränser per område
Aggregator
    ACCUM_ATTRS_NAME = Merge Incoming Attributes
    GROUP_BY = xml_parent_id
    LIST_ATTRS_TO_INCLUDE = minus.href plus.href xml_parent_child_pos
    LIST_NAME = childList
    MODE = Attributes Only
    ORDERED = No
    SEP = ,
    AGGREGATE -> PolygonCreator
Note: Create ID for later join
AttributeCreator_2
    ATTR_TABLE = SET_TO ID_join = #@Value(gml_id)
    -> PolygonCreator
Note: Creates polygons over Områden.
PolygonCreator: PythonCaller
    PYTHONSOURCE:
      import fme
      import fmeobjects

      # Finds and returns the requested gräns
      def gransFinder(id,gransList):
          for grans in gransList:
              if grans.getAttribute('ID_join') == id:
                  return grans

      # Finds first line segment in a boundary, either outer or inner polygon
      def initialBoundaryLine(polygonBoundaryParts):
          geo = polygonBoundaryParts.getGeometry()

          nbrLines = geo.numParts()

          # Taking first part of the FMEPath
          polygonBoundary = geo.getPartAt(0)

          if type(polygonBoundary) == fmeobjects.FMEArc:
              polygonBoundary = polygonBoundary.getAsLine()

          # Iterating over the parts in the FMEPath object
          for tp in xrange(1,nbrLines):
              tpl = geo.getPartAt(tp) # Next part (at index tp)

              # Needs to be an FMELine
              if type(tpl) == fmeobjects.FMEArc:
                  tpl = tpl.getAsLine()

              polygonBoundary.appendLine(tpl)

          return polygonBoundary

      # #################################################################
      # FeatureProcessor
      # #################################################################
      class FeatureProcessor(object):
          def __init__(self):
              self.omrade = []
              self.grans = []

          # Saving in different lists depending on if the feature is a gräns or område
          def input(self,feature):
              if feature.hasGeometry():
                  self.grans.append(feature)
              else:
                  self.omrade.append(feature)

          def close(self):

              # Iterating over all Områden sent to the PythonCaller
              for omr in self.omrade:
                  boundaryList = []
                  tempGrans = True # Will stop the loop after last item is found (temp = None)
                  index = 0 # Index of "Gräns"
                  innerIndex = 0 # For keeping track of holes
                  firstLine = True # If first line segment of a gräns

                  #Looping over all "gränser" in current "Område"
                  while tempGrans != None:
                      tempGrans = omr.getAttribute('childList{%i}.xml_parent_child_pos' % (index))

                      # Already found last "gräns" of the "område"
                      if not tempGrans:
                          break
                      tempGrans = int(tempGrans)

                      if not tempGrans == index: # To break in case something is wrong wth indices
                          print 'Index not correct'
                          break

                      # Retreiving the next segment and finding direction.
                      minusTest = omr.getAttribute('childList{%i}.minus.href' % (index))
                      if minusTest != None:
                          minus = True
                          tempGransID = minusTest
                      else:
                          minus = False
                          tempGransID = omr.getAttribute('childList{%i}.plus.href' % (index))

                      # Building line
                      # This part is for the first "Gräns" either in the outer (index == 0) polygon or
                      # a hole (innerIndex >= 1)
                      if firstLine:
                          partOne = gransFinder(tempGransID, self.grans)
                          polygonBoundary = initialBoundaryLine(partOne)
                          firstLine = False
                          if minus:
                              polygonBoundary.reverse()


                      # From the second "gräns" in the list.
                      else:
                          polygonBoundaryParts = gransFinder(tempGransID, self.grans)

                          geo = polygonBoundaryParts.getGeometry()

                          nbrLines = geo.numParts()

                          tmpLine = geo.getPartAt(0)

                          if type(tmpLine) == fmeobjects.FMEArc:
                              tmpLine = tmpLine.getAsLine()

                          #Iterating over the of the parts in the FMEPath object
                          for tp in xrange(1,nbrLines):

                              tpl = geo.getPartAt(tp)

                              if type(tpl) == fmeobjects.FMEArc:
                                  tpl = tpl.getAsLine()

                              tmpLine.appendLine(tpl)

                          if minus:
                              tmpLine.reverse()

                          polygonBoundary.appendLine(tmpLine)

                      # True if a closed polygon is found.
                      if polygonBoundary.isClosed(False): # False => not considering 3D
                          firstLine = True # Next will be first line of an inner polygon (if existing)
                          innerIndex += 1 # Counting inner polygons
                          boundaryList.append(polygonBoundary) # Appending current polygon to list
                          polygonBoundary = None

                      index += 1

                  # Final part: Creating the polygons incl. holes if present
                  # Creating a polygon with the outer boundary by popping it from the list of ploygons
                  if boundaryList:
                      outerPoly = fmeobjects.FMEDonut(boundaryList.pop(0))
                      # Iterating over all inner polygons that were found (the ouoter is already removed above)
                      for omrPoly in boundaryList:
                          innerPoly = fmeobjects.FMEDonut(omrPoly)
                          outerPoly.addInnerBoundaryCurve(omrPoly)

                      omr.setGeometry(outerPoly)

                      self.pyoutput(omr)
    PYTHONSYMBOL = FeatureProcessor
    -> FeatureMerger_2 [REQUESTOR]
Note: Needs xml_id from the / XML-reader to join with lines.
FeatureMerger
    ATTR_ACCUM_MODE = Merge Supplier
    ATTR_CONFLICT_RES = Use Requestor
    CLEANING_TOLERANCE = None
    IGNORE_NULLS = No
    JOIN_KEYS = @Value(gml_id) @Value(DP_Omrade.id) AUTO
    MERGE_TYPE = Attributes Only
    PROCESS_DUPS = No
    REJECT_NULL_MISSING_KEYS = No
    SUPPLIERS_FIRST = No
    MERGED -> AttributeKeeper
AttributeKeeper
    KEEP_ATTRS = xml_id,gml_id,xml_fragment,DP_Omrade.id,gml_parent_id
    -> AttributeCreator
AttributeCreator
    ATTR_TABLE = SET_TO ID_join = #@Value(DP_Omrade.id)
    -> FeatureMerger_Egenskap [REQUESTOR]
AttributeRemover
    REMOVE_ATTRS = minus,plus
    -> FeatureMerger_2 [SUPPLIER]
Note: Adding Geometries to bestämmelser
FeatureMerger_2
    ATTR_ACCUM_MODE = Merge Supplier
    ATTR_CONFLICT_RES = Use Requestor
    IGNORE_NULLS = No
    JOIN_KEYS = @Value(xml_parent_id) @Value(xml_id) AUTO
    MERGE_TYPE = Attributes and Geometry
    PROCESS_DUPS = NO
    REJECT_NULL_MISSING_KEYS = No
    SUPPLIERS_FIRST = No
    MERGED -> AttributeRemover_3
AttributeRemover_3
    LIST_ATTRS = childList{}
    REMOVE_ATTRS = xml_id,gml_id,xml_parent_child_pos,ID_join,plus.href,xml_matched_element,plus,minus.href,linje
    -> AreaCalculator_detailedDevelopmentPlan
AttributeRemover_areaWithBuilding
    LIST_ATTRS = administrativBestammelse{} administrativBestammelse{}.gml_remoteSchema administrativBestammelse{}.nilReason administrativBestammelse{}.owns administrativBestammelse{}.xlink_href administrativBestammelse{}.xlink_title egenskapsbestammelse{} egenskapsbestammelse{}.gml_remoteSchema egenskapsbestammelse{}.nilReason egenskapsbestammelse{}.owns egenskapsbestammelse{}.xlink_href egenskapsbestammelse{}.xlink_title
    REMOVE_ATTRS = bestammelseid,beteckning,bestammelsetyp,anvandningsslag
    -> PythonCaller_RegulationTester
Note: Checks regulations in the detailed development plan against the building model. Currently the regulations are checked by looping over the valid regulations in the area the building will be located in. Since there is a very large number of possible regulations a look-up table of regulations is simulated with if-elif in this case study.
PythonCaller_RegulationTester
    NEW_ATTRIBUTES = testResults numberTests
    PYTHONSOURCE:
      # -*- coding: utf-8 -*-

      import fme
      import fmeobjects
      import xlsxwriter

      # #################################################################
      # FeatureProcessor
      # #################################################################
      class FeatureProcessor(object):
          def __init__(self):
              self.omrade = None
              self.building = None
              self.allTests = True # Will be changed to Fail if any test fails
              self.nbrTest = 0 # Counting the number of regulations tested

          # Saving as different attributes depending on if the feature is a building or område
          def input(self,feature):
              if feature.getAttribute('_byggnadsArea_sqm'):
                  self.building = feature
              else:
                  self.omrade = feature

          def close(self):

              # ##########################################################################################
              # Creating Excel sheet for saving the results
              # Excel sheets, path and name given as user parameter:
              xlsSheet = FME_MacroValues['XlsReport']

              # Create an new Excel file and add a worksheet.
              workbook = xlsxwriter.Workbook(xlsSheet)

              # ##########################################################################################
              # First testing användningsbestämmelser
              i = 0
              # Classification DP_KM_S_For etc. is given as anvandningsslag
              item = self.omrade.getAttribute('AnvandningsBestList{%i}.anvandningsslag' % (i))

              # Adding info to report if any användningsbestämmelse
              if item:
                  # Add a worksheet for anvandningsbestammelser
                  worksheet = workbook.add_worksheet('Anvandningsbestammelse')
                  worksheet.write(0, 0, 'Bestammelse')
                  worksheet.write(0, 1, 'Byggnad varde')
                  worksheet.write(0, 2, 'Godkand')

              while item:

                  testResult = None
                  # Simulating look-up table with all regulations with if-statement
                  if item == 'DP_KM_S_For':
                      buildFunc = self.building.getAttribute('Building.buildingPart.BuildingPart.function')
                      # "Simple" way of handling encoding for 'ö'
                      if buildFunc[2:] == 'rskola':
                          buildFunc = 'Forskola' # Ugly way of handling the 'ö' in förskola....
                          testResult = 'Pass'
                      else:
                          testResult = 'Fail'
                          self.allTests = False

                  # Adding result to report
                  worksheet.write(i+1, 0, item)
                  worksheet.write(i+1, 1, buildFunc)
                  worksheet.write(i+1, 2, testResult)

                  i += 1
                  item = self.omrade.getAttribute('AnvandningsBestList{%i}.anvandningsslag' % (i))

              self.nbrTest += i # First test is index 0 so i will giev the actual number of tests performed

              # ##########################################################################################
              # Second testing egenskapsbestämmelser
              i = 0
              # Classification DP_KM_Eg_Omfatt_Byggnadsarea_Kvm etc. is given as bestammelsetyp
              item = self.omrade.getAttribute('EgenskapsBestList{%i}.bestammelsetyp' % (i))

              # Adding info to report if any egenskapsbestämmelse
              if item:
                  # Add a worksheet for anvandningsbestammelser
                  worksheet = workbook.add_worksheet('Egenskapsbestammelse')
                  worksheet.write(0, 0, 'Bestammelse')
                  worksheet.write(0, 1, 'Specificering')
                  worksheet.write(0, 2, 'Best. varde')
                  worksheet.write(0, 3, 'Byggnad varde')
                  worksheet.write(0, 4, 'Godkand')

              while item:
                  # Simulating look-up table with all regulations with if-statement
                  if item == 'DP_KM_Eg_Omfatt_Byggnadsarea_Kvm':
                      # exploatering => densification given as %
                      areaType = self.omrade.getAttribute('EgenskapsBestList{%i}.variabel{0}.DP_VarDecimaltal.namn' % (i))
                      areaValue = float(self.omrade.getAttribute('EgenskapsBestList{%i}.variabel{0}.DP_VarDecimaltal.varde' % (i)))
                      areaOmrade = float(self.omrade.getAttribute('_area_omrade'))
                      buildArea = float(self.building.getAttribute('_byggnadsArea_sqm'))

                      # Adding result to report
                      worksheet.write(i+1, 0, item)
                      worksheet.write(i+1, 1, areaType)
                      worksheet.write(i+1, 2, areaValue)
                      worksheet.write(i+1, 3, round(buildArea/areaOmrade*100))

                      if areaType == 'exploatering':
                          if areaOmrade*areaValue/100 > buildArea:
                              worksheet.write(i+1, 4, 'Pass')
                              print 'Egenskapsstest building area PASSED!!!!'
                          else:
                              worksheet.write(i+1, 4, 'Fail')
                              self.allTests = False

                  elif item == 'DP_KM_Eg_Omfatt_VanAnt_Exakt_Aldre':

                      spec = self.omrade.getAttribute('EgenskapsBestList{%i}.variabel{0}.DP_VarDecimaltal.namn' % (i))
                      specValue = float(self.omrade.getAttribute('EgenskapsBestList{%i}.variabel{0}.DP_VarDecimaltal.varde' % (i)))
                      buildValue = float(self.building.getAttribute('Building.storeysAboveGround'))

                      # Adding result to report
                      worksheet.write(i+1, 0, item)
                      worksheet.write(i+1, 2, specValue)
                      worksheet.write(i+1, 3, buildValue)

                      if buildValue <= specValue:
                          worksheet.write(i+1, 4, 'Pass')
                          print 'Egenskapsstest building area PASSED!!!!'
                      else:
                          worksheet.write(i+1, 4, 'Fail')
                          self.allTests = False

                  i += 1
                  item = self.omrade.getAttribute('EgenskapsBestList{%i}.bestammelsetyp' % (i))

              self.nbrTest += i # First test is index 0 so i will giev the actual number of tests performed

              # Closing the Excel sheet used for report
              workbook.close()



              # ##########################################################################################
              # Adding attribute with result (Pass/Fail) from the test
              self.building.setAttribute('testResult', self.allTests)
              self.building.setAttribute('numberTests', self.nbrTest)

              self.pyoutput(self.building)
    PYTHONSYMBOL = FeatureProcessor
    -> PythonCaller_RegulationTester_Output
PythonCaller_RegulationTester_Output: Inspector

Bookmark: Reading CityGML3 ADE building model and scales + transforms it to SWEREF99 TM
  NB, only need the scaler when original building model has unit mm.
cityObjectMember (reader XML_2)
    attributes: Building.boundedBy.Envelope.lowerCorner xml_char(37), Building.boundedBy.Envelope.srsDimension xml_decimal(2,0), Building.boundedBy.Envelope.srsName xml_char(27), Building.boundedBy.Envelope.upperCorner xml_char(37), Building.buildingPart.BuildingPart.boundedBy.Envelope.lowerCorner xml_char(37), Building.buildingPart.BuildingPart.boundedBy.Envelope.srsDimension xml_decimal(2,0), Building.buildingPart.BuildingPart.boundedBy.Envelope.srsName xml_char(27), Building.buildingPart.BuildingPart.boundedBy.Envelope.upperCorner xml_char(37), Building.buildingPart.BuildingPart.buildingSpace.ConstructionSpace.lod2Solid.MultiSolid.id xml_char(42), Building.buildingPart.BuildingPart.buildingSpace.ConstructionSpace.lod2Solid.MultiSolid.solidMember.Solid.exterior.Shell.surfaceMember{}.Surface.id xml_char(44), Building.buildingPart.BuildingPart.buildingSpace.ConstructionSpace.lod2Solid.MultiSolid.solidMember.Solid.exterior.Shell.surfaceMember{}.Surface.patches.PolygonPatch.exterior.LinearRing.posList xml_char(5343), Building.buildingPart.BuildingPart.buildingSpace.ConstructionSpace.lod2Solid.MultiSolid.solidMember.Solid.id xml_char(42), Building.buildingPart.BuildingPart.buildingSpace.ConstructionSpace.lod2Solid.MultiSolid.srsDimension xml_decimal(2,0), Building.buildingPart.BuildingPart.buildingSpace.ConstructionSpace.lod2Solid.MultiSolid.srsName xml_char(15), Building.buildingPart.BuildingPart.class xml_char(17), Building.buildingPart.BuildingPart.class.codeSpace xml_char(29), Building.buildingPart.BuildingPart.id xml_char(40), Building.buildingPart.BuildingPart.kallare xml_boolean, Building.buildingSpace xml_char(1), Building.buildingSpace.nilReason xml_char(13), Building.byggnadArea xml_decimal(11,0), Building.id xml_char(40), xml_fragment xml_xml, xml_id xml_char(24), xml_matched_element xml_char(17), xml_parent_child_pos xml_char(1), xml_parent_id xml_char(1)
    -> GeometryReplacer
GeometryReplacer
    KIND_LONG = GML
    REMOVE_ATTRIBUTE = Yes
    SOURCE = @Value(xml_fragment)
    SRS_AXIS_ORDER_DISPLAY = Automatic
    -> Scaler
Scaler
    RASTER_SCALING = Extents
    SCALE_ORIGIN = 0,0
    TEXT_LOC_ONLY = Location and Size
    XSCALE = 0.001
    YSCALE = 0.001
    ZSCALE = 0.001
    SCALED -> CsmapReprojector_2
CsmapReprojector_2
    DEST = SWEREF-99-TM
    INTERPOLATION_TYPE_NAME = Nearest Neighbor
    RASTER_CELL_SIZE = Preserve Cells
    RASTER_TOLERANCE = 0.0
    SOURCE = SWEREF-99-13-30
    VERTICAL_HANDLING = Ignore heights and leave them unchanged
    REPROJECTED -> Deaggregator

Bookmark: To get building only
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> Tester_BuildingExtractor
Tester_BuildingExtractor
    BOOL_OP = OR
    TEST_CLAUSE = TEST @Value(_part_number) = 2
    PASSED -> SurfaceFootprintReplacer
    PASSED -> AppearanceSetter_LOD1_building [GEOMETRY]

Bookmark: To get footprint and expose (+ keep) required attributes.
SurfaceFootprintReplacer
    LIGHT_X = 0
    LIGHT_Y = 0
    LIGHT_Z = 1
    OFFSET_Z = 0
    SHADOW_MODE = Overhead Shadow
    FOOTPRINT -> AttributeExposer
AttributeExposer
    ATTR_LIST = Building.storeysAboveGround,Building.buildingPart.BuildingPart.function,Building.id,Building.id
    -> AreaCalculator
AreaCalculator
    AREA_ATTR = _byggnadsArea_sqm
    AREA_TYPE = Plane Area
    MULT = 1
    -> AttributeRounder_2
AttributeRounder_2
    PLACES = 0
    ROUND_TYPE = Nearest
    SRC_ATTRS = _byggnadsArea_sqm
    -> AttributeKeeper_buildingFootprint
AttributeKeeper_buildingFootprint
    KEEP_ATTRS = Building.buildingPart.BuildingPart.class,_byggnadsArea_sqm,_geometry_name,Building.id,Building.buildingPart.BuildingPart.function,Building.byggnadArea,Building.buildingPart.BuildingPart.kallare,Building.storeysAboveGround
    -> Clipper [CLIPPER]
    -> PythonCaller_RegulationTester
    -> FeatureColorSetter

Bookmark: Detaljplan (DP_Område) from XML-reader
DP_Omrade (reader XML_1)
    attributes: DP_Omrade.id xml_char(3), minus xml_char(1), minus.href xml_char(6), minus{} xml_char(1), minus{}.href xml_char(6), plus xml_char(1), plus.href xml_char(6), plus{} xml_char(1), plus{}.href xml_char(6), xml_fragment xml_xml, xml_id xml_char(21), xml_matched_element xml_char(10), xml_parent_child_pos xml_char(1), xml_parent_id xml_char(1)
    -> FeatureMerger [SUPPLIER]
minus (reader XML_1)
    attributes: minus xml_char(1), minus.href xml_char(6), xml_fragment xml_xml, xml_id xml_char(20), xml_matched_element xml_char(6), xml_parent_child_pos xml_decimal(3,0), xml_parent_id xml_char(21)
    -> Aggregator
plus (reader XML_1)
    attributes: plus xml_char(1), plus.href xml_char(6), xml_fragment xml_xml, xml_id xml_char(19), xml_matched_element xml_char(5), xml_parent_child_pos xml_decimal(3,0), xml_parent_id xml_char(21)
    -> Aggregator

Bookmark: Detaljplan from GML-reader
DP_Grans (reader GML_1)
    attributes: typ{} xml_char(5), linje xml_geometry
    -> AttributeCreator_2
DP_Planbestammelse (reader GML_1)
    attributes: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
DP_Egenskapsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> FeatureMerger_Egenskap [SUPPLIER]
DP_Plan (reader GML_1)
    attributes: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
DP_Omrade (reader GML_1)
    attributes: plus.nilReason xml_buffer, plus.gml_remoteSchema xml_buffer, plus.xlink_href xml_buffer, plus.xlink_title xml_buffer, plus.owns xml_boolean, minus.nilReason xml_buffer, minus.gml_remoteSchema xml_buffer, minus.xlink_href xml_buffer, minus.xlink_title xml_buffer, minus.owns xml_boolean
    -> FeatureMerger [REQUESTOR]
DP_Data (reader GML_1)
    attributes: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
DP_Anvandningsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, anvandningsslag xml_buffer, precisering xml_buffer, huvudsaklig xml_boolean, egenskapsbestammelse{}.nilReason xml_buffer, egenskapsbestammelse{}.gml_remoteSchema xml_buffer, egenskapsbestammelse{}.xlink_href xml_buffer, egenskapsbestammelse{}.xlink_title xml_buffer, egenskapsbestammelse{}.owns xml_boolean, administrativBestammelse{}.nilReason xml_buffer, administrativBestammelse{}.gml_remoteSchema xml_buffer, administrativBestammelse{}.xlink_href xml_buffer, administrativBestammelse{}.xlink_title xml_buffer, administrativBestammelse{}.owns xml_boolean
    -> FeatureMerger_Anvandning [SUPPLIER]
DP_AdministrativBestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> FeatureMerger_Administrativ [SUPPLIER]

Bookmark: Connects bestämmelser to områden
FeatureMerger_Egenskap
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(ID_join) @Value(omrade.xlink_href) AUTO
    LIST_ATTRS_TO_INCLUDE = anmarkning bestammelseid bestammelsetyp beteckning giltighet ursprunglig uuid variabel{}.DP_VarArtal.namn variabel{}.DP_VarArtal.varde variabel{}.DP_VarDatum.namn variabel{}.DP_VarDatum.varde variabel{}.DP_VarDecimaltal.namn variabel{}.DP_VarDecimaltal.varde variabel{}.DP_VarHeltal.namn variabel{}.DP_VarHeltal.varde variabel{}.DP_VarKod.namn variabel{}.DP_VarKod.varde variabel{}.DP_VarLinje.namn variabel{}.DP_VarLinje.varde variabel{}.DP_VarPunkt.namn variabel{}.DP_VarPunkt.varde variabel{}.DP_VarText.namn variabel{}.DP_VarText.varde variabel{}.owns
    LIST_NAME = EgenskapsBestList
    MERGE_TYPE = Attributes Only
    PROCESS_DUPS = YES
    REJECT_NULL_MISSING_KEYS = No
    SUPPLIERS_FIRST = No
    MERGED -> FeatureMerger_Anvandning [REQUESTOR]
    UNMERGED_REQUESTOR -> FeatureMerger_Anvandning [REQUESTOR]
FeatureMerger_Anvandning
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(ID_join) @Value(omrade.xlink_href) AUTO
    LIST_ATTRS_TO_INCLUDE = anmarkning anvandningsslag bestammelseid beteckning giltighet ursprunglig uuid
    LIST_NAME = AnvandningsBestList
    MERGE_TYPE = Attributes Only
    PROCESS_DUPS = YES
    REJECT_NULL_MISSING_KEYS = No
    SUPPLIERS_FIRST = No
    MERGED -> FeatureMerger_Administrativ [REQUESTOR]
    UNMERGED_REQUESTOR -> FeatureMerger_Administrativ [REQUESTOR]
FeatureMerger_Administrativ
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(ID_join) @Value(omrade.xlink_href) AUTO
    LIST_ATTRS_TO_INCLUDE = anmarkning bestammelseid bestammelsetyp beteckning giltighet ursprunglig uuid variabel{}.DP_VarArtal.namn variabel{}.DP_VarArtal.varde variabel{}.DP_VarDatum.namn variabel{}.DP_VarDatum.varde variabel{}.DP_VarDecimaltal.namn variabel{}.DP_VarDecimaltal.varde variabel{}.DP_VarHeltal.namn variabel{}.DP_VarHeltal.varde variabel{}.DP_VarKod.namn variabel{}.DP_VarKod.varde variabel{}.DP_VarLinje.namn variabel{}.DP_VarLinje.varde variabel{}.DP_VarPunkt.namn variabel{}.DP_VarPunkt.varde variabel{}.DP_VarText.namn variabel{}.DP_VarText.varde variabel{}.owns
    LIST_NAME = AdministrativBestList
    MERGE_TYPE = Attributes Only
    PROCESS_DUPS = YES
    REJECT_NULL_MISSING_KEYS = No
    SUPPLIERS_FIRST = No
    MERGED -> AttributeRemover
    UNMERGED_REQUESTOR -> AttributeRemover

Bookmark: Need area to calcualte densification
AreaCalculator_detailedDevelopmentPlan
    AREA_ATTR = _area_omrade
    AREA_TYPE = Plane Area
    MULT = 1
    -> AttributeRounder
AttributeRounder
    PLACES = 0
    ROUND_TYPE = Nearest
    SRC_ATTRS = _area_omrade
    -> TestFilter_3

Bookmark: Filtering by land use (anvandningsslag) to color by land use group.
TestFilter_3
    DEFAULT_VALUE = <UNFILTERED>
    TEST_LIST = "BOOL_OP,OR,COMPOSITE_TEST,""""""<Unused>"""""",TEST_CLAUSE,CASE_INSENSITIVE_TEST @Value(anvandningsslag) CONTAINS _W_",Water,"BOOL_OP,OR,COMPOSITE_TEST,""""""<Unused>"""""",TEST_CLAUSE,CASE_INSENSITIVE_TEST @Value(anvandningsslag) CONTAINS gata",Gata,"BOOL_OP,OR,COMPOSITE_TEST,""""""<Unused>"""""",TEST_CLAUSE,TEST @Value(uuid) = 3b2de3e5-2ea1-4233-b48e-54f4c87a0a10",EntirePlan,"BOOL_OP,OR,COMPOSITE_TEST,""""""<Unused>"""""",TEST_CLAUSE,CASE_INSENSITIVE_TEST @Value(anvandningsslag) CONTAINS gang",Pedestrian_bike,"BOOL_OP,OR,COMPOSITE_TEST,""""""<Unused>"""""",TEST_CLAUSE,CASE_INSENSITIVE_TEST @Value(EgenskapsBestList{0}.bestammelsetyp) CONTAINS Prickmark",Prickmark,"BOOL_OP,OR,COMPOSITE_TEST,""""""<Unused>"""""",TEST_CLAUSE,CASE_INSENSITIVE_TEST @Value(anvandningsslag) CONTAINS Natur",Natur,"BOOL_OP,OR,COMPOSITE_TEST,""""""<Unused>"""""",TEST_CLAUSE,CASE_INSENSITIVE_TEST @Value(anvandningsslag) CONTAINS park",Park
    Water -> FeatureColorSetter_Water
    Gata -> FeatureColorSetter_gata
    EntirePlan -> FeatureColorSetter_EntirePlan
    Pedestrian_bike -> FeatureColorSetter_pedestrian_bike
    Prickmark -> FeatureColorSetter_prickmark
    Natur -> FeatureColorSetter_natur
    Park -> FeatureColorSetter_park
    <UNFILTERED> -> FeatureColorSetter_others
FeatureColorSetter_Water
    FILL_COLOR = 0,0,1
    MODE = Fixed
    COLORED -> FeatureColorSetter_Water_Colored
FeatureColorSetter_Water_Colored: Inspector
FeatureColorSetter_gata
    COLOR = 0.666667,0.666667,0.498039
    FILL_COLOR = 0.196078,0.196078,0.145098
    MODE = Fixed
    COLORED -> FeatureColorSetter_gata_Colored
FeatureColorSetter_gata_Colored: Inspector
FeatureColorSetter_EntirePlan
    COLOR = 0.666667,0,0
    MODE = Fixed
    COLORED -> FeatureColorSetter_EntirePlan_Colored
FeatureColorSetter_EntirePlan_Colored: Inspector
FeatureColorSetter_pedestrian_bike
    COLOR = 0.666667,0.666667,0.498039
    FILL_COLOR = 0.372549,0.372549,0.278431
    MODE = Fixed
    COLORED -> FeatureColorSetter_pedestrian_bike_Colored
FeatureColorSetter_pedestrian_bike_Colored: Inspector
FeatureColorSetter_prickmark
    COLOR = 1,0,0
    FILL_COLOR = 1,0,0
    MODE = Fixed
    COLORED -> FeatureColorSetter_prickmark_Colored
FeatureColorSetter_prickmark_Colored: Inspector
FeatureColorSetter_natur
    COLOR = 0,0.666667,0
    FILL_COLOR = 0,0.666667,0
    MODE = Fixed
    COLORED -> FeatureColorSetter_natur_Colored
FeatureColorSetter_natur_Colored: Inspector
FeatureColorSetter_park
    COLOR = 0,1,0
    FILL_COLOR = 0,1,0
    MODE = Fixed
    COLORED -> FeatureColorSetter_park_Colored
FeatureColorSetter_park_Colored: Inspector
FeatureColorSetter_others
    COLOR = 0,0,0
    FILL_COLOR = 1,1,0.498039
    MODE = Fixed
    COLORED -> FeatureColorSetter_others_Colored
    COLORED -> Clipper [CLIPPEE]
    COLORED -> FeatureMerger_5 [SUPPLIER]
FeatureColorSetter_others_Colored: Inspector

Bookmark: To find in which area the building is located
Note: To find in which area the building is located
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> AttributeKeeper_3
AttributeKeeper_3
    KEEP_ATTRS = DP_Omrade.id
    -> FeatureMerger_5 [REQUESTOR]
FeatureMerger_5
    ATTR_ACCUM_MODE = Merge Supplier
    ATTR_CONFLICT_RES = Use Requestor
    IGNORE_NULLS = No
    JOIN_KEYS = @Value(DP_Omrade.id) @Value(DP_Omrade.id) AUTO
    MERGE_TYPE = Attributes and Geometry
    PROCESS_DUPS = NO
    REJECT_NULL_MISSING_KEYS = No
    SUPPLIERS_FIRST = No
    MERGED -> AttributeRemover_areaWithBuilding

Bookmark: Final result of test
Note: Planned to test true - false and colour the building with green or red depending on the result but didn't get the tester to work. From a search it seems to be a bug in FME2018.
Tester_2
    BOOL_OP = OR
    TEST_CLAUSE = CASE_INSENSITIVE_TEST @Value(testResults) = true
    PASSED -> FeatureColorSette_Passed
    FAILED -> FeatureColorSette_Failed
FeatureColorSette_Passed: FeatureColorSetter
    COLOR = 0,1,0
    FILL_COLOR = 0,1,0
    MODE = Fixed
    COLORED -> FeatureColorSette_Passed_Colored
FeatureColorSette_Passed_Colored: Inspector
FeatureColorSette_Failed: FeatureColorSetter
    COLOR = 1,0,0
    FILL_COLOR = 1,0,0
    MODE = Fixed
    COLORED -> FeatureColorSette_Failed_Colored
FeatureColorSette_Failed_Colored: Inspector
