FME workspace MinZhang_placement_parking.fmwt
Title: detaljPlanReader_multiHoles_Karlstad_verII

Parameters:
- SourceDataset_GML_5 = $(FME_MF_DIR)2/test_Karlstad/karlstad.xml   # Source Geography Markup Language (GML) File(s)
- SourceDataset_XML = $(FME_MF_DIR)2/test_Karlstad/karlstad.xml   # Source XML File(s)
- SourceDataset_ESRISHAPE = $(FME_MF_DIR)3/wb_template_1563888728128_516/Lotsen_IFC_footprint.shp   # Source Esri Shapefile(s)
- min_dist = 4.5   # " " min_dist_build

Readers:
- GML_1: GML from $(SourceDataset_GML_5) in SWEREF-99-TM
- XML_1: XML from $(SourceDataset_XML) in SWEREF-99-TM
- ESRISHAPE_1: ESRISHAPE from $(SourceDataset_ESRISHAPE) in SWEREF-99-TM

Lotsen_IFC_footprint (reader ESRISHAPE_1)
    attributes: BYGGNADS_I char(200), CoClass_By char(200), CoClass_00 char(200), CoClass_Fu char(200), CoClass_01 char(200), CoClass_Ko char(200), CoClass_02 char(200), GlobalId char(22), Descriptio char(254), FootPrint char(254), Coclass char(200), Coordinate char(200), CoClass char(200), Byggnadsve char(200), Funktionel char(200)
    -> CenterPointExtractor
    -> CsmapReprojector_2
Note: Find out where the house is located so I can move it back to origin
CenterPointExtractor
    CENTX = _inside_x
    CENTY = _inside_y
    CENTZ = _inside_z
    MODE = Center
CsmapReprojector_2
    DEST = SWEREF-99-TM
    INTERPOLATION_TYPE_NAME = Nearest Neighbor
    RASTER_CELL_SIZE = Preserve Cells
    RASTER_TOLERANCE = 0.0
    VERTICAL_HANDLING = Ignore heights and leave them unchanged
    REPROJECTED -> Offset_to_origin
Offset_to_origin: Offsetter
    MODE = Cartesian Coordinate
    XOFF = -415384.5523
    YOFF = -6582378.9311
    ZOFF = 0
    OFFSET -> Rotator
Rotator
    ANGLE = 0
    XORIG = 0
    YORIG = 0
    ROTATED -> Offsetter
Note: CHANG COORDINATES HERE!!!!
Offsetter
    MODE = Cartesian Coordinate
    XOFF = 415342
    YOFF = 6582600
    ZOFF = 0
    OFFSET -> House_Color
    OFFSET -> Bufferer
House_Color: FeatureColorSetter
    COLOR = 0,0.666667,1
    FILL_COLOR = 0.341176,0.768627,1
    MODE = Fixed
    COLORED -> House
    COLORED -> AreaOnAreaOverlayer_3 [AREA] [off]
    COLORED -> Clipper_2 [CLIPPER]
    COLORED -> SpatialFilter_5 [Filter]
    COLORED -> MinDistance [SpatialFilter_Filter]
    COLORED -> MinDistance [NeighborFinder_Candidate]
    COLORED -> NeighborFinder_2 [CANDIDATE]
House: Inspector
Bufferer
    ANGLE = 22.5
    CAP_STYLE = Round
    CORNER_STYLE = Round
    MODE = AREA
    OFFSET = -0.001
    BUFFERED -> SpatialFilter_4 [Filter]
CsmapReprojector_5
    DEST = SWEREF-99-TM
    INTERPOLATION_TYPE_NAME = Nearest Neighbor
    RASTER_CELL_SIZE = Preserve Cells
    RASTER_TOLERANCE = 0.0
    VERTICAL_HANDLING = Ignore heights and leave them unchanged
    REPROJECTED -> AttributeCreator_2
Note: Create ID for later join
AttributeCreator_2
    ATTR_TABLE = SET_TO ID_join = #@Value(gml_id)
    -> PolygonCreator
CsmapReprojector_3
    DEST = SWEREF-99-TM
    INTERPOLATION_TYPE_NAME = Nearest Neighbor
    RASTER_CELL_SIZE = Preserve Cells
    RASTER_TOLERANCE = 0.0
    VERTICAL_HANDLING = Ignore heights and leave them unchanged
    REPROJECTED -> FeatureMerger_Egenskap [SUPPLIER]
CsmapReprojector_4
    DEST = SWEREF-99-TM
    INTERPOLATION_TYPE_NAME = Nearest Neighbor
    RASTER_CELL_SIZE = Preserve Cells
    RASTER_TOLERANCE = 0.0
    VERTICAL_HANDLING = Ignore heights and leave them unchanged
    REPROJECTED -> FeatureMerger [REQUESTOR]
CsmapReprojector_6
    DEST = SWEREF-99-TM
    INTERPOLATION_TYPE_NAME = Nearest Neighbor
    RASTER_CELL_SIZE = Preserve Cells
    RASTER_TOLERANCE = 0.0
    VERTICAL_HANDLING = Ignore heights and leave them unchanged
    REPROJECTED -> FeatureMerger_Anvandning [SUPPLIER]
CsmapReprojector_7
    DEST = SWEREF-99-TM
    INTERPOLATION_TYPE_NAME = Nearest Neighbor
    RASTER_CELL_SIZE = Preserve Cells
    RASTER_TOLERANCE = 0.0
    VERTICAL_HANDLING = Ignore heights and leave them unchanged
    REPROJECTED -> FeatureMerger_Administrativ [SUPPLIER]
Note: Needs xml_id from the / XML-reader to join with lines.
FeatureMerger
    ATTR_ACCUM_MODE = Merge Supplier
    ATTR_CONFLICT_RES = Use Requestor
    CLEANING_TOLERANCE = None
    IGNORE_NULLS = No
    JOIN_KEYS = @Value(gml_id) @Value(DP_Omrade.id) AUTO
    MERGE_TYPE = Attributes Only
    PROCESS_DUPS = No
    REJECT_NULL_MISSING_KEYS = No
    SUPPLIERS_FIRST = No
    MERGED -> AttributeKeeper
AttributeKeeper
    KEEP_ATTRS = xml_id,gml_id,xml_fragment,DP_Omrade.id,gml_parent_id
    -> AttributeCreator
AttributeCreator
    ATTR_TABLE = SET_TO ID_join = #@Value(DP_Omrade.id)
    -> FeatureMerger_Egenskap [REQUESTOR]
AttributeRemover
    REMOVE_ATTRS = minus,plus
    -> FeatureMerger_2 [SUPPLIER]
Note: Workspace för att importera en detaljplan enligt SS 637040 och kontrollera att byggnaden ligger i tillåtet område samt att det finns parkeringsmöjligheter. / Polygoner för områden i detaljplanen skapas och bestämmelser kopplas till polygonerna. Workspacet hanterar inte kartografin utan ska ses som ett verktyg för att hantera bestämmelser vid kontroll av bygglov. Bestämmelser och information som gäller för hela planen kopplas inte till något område. / Referenssystem fås som attribut i DP_Plan
Note: This workspace is released under the 3-Clause BSD License. For details, see https://opensource.org/licenses/BSD-3-Clause / Framtagandet är finansierat av: / Projektet Får Jag Lov koordinerat av Boverket. / Copyright (c) 2018, Lunds universitet / All rights reserved.
Note: Create list with gränser per område
Aggregator
    ACCUM_ATTRS_NAME = Merge Incoming Attributes
    GROUP_BY = xml_parent_id
    LIST_ATTRS_TO_INCLUDE = minus.href plus.href xml_parent_child_pos
    LIST_NAME = childList
    MODE = Attributes Only
    ORDERED = No
    SEP = ,
    AGGREGATE -> PolygonCreator
Note: Creates polygons over Områden.
PolygonCreator: PythonCaller
    PYTHONSOURCE:
      import fme
      import fmeobjects

      # Finds and returns the requested gräns
      def gransFinder(id,gransList):
          for grans in gransList:
              if grans.getAttribute('ID_join') == id:
                  return grans

      # Finds first line segment in a boundary, either outer or inner polygon
      def initialBoundaryLine(polygonBoundaryParts):
          geo = polygonBoundaryParts.getGeometry()

          nbrLines = geo.numParts()

          # Taking first part of the FMEPath
          polygonBoundary = geo.getPartAt(0)

          if type(polygonBoundary) == fmeobjects.FMEArc:
              polygonBoundary = polygonBoundary.getAsLine()

          # Iterating over the parts in the FMEPath object
          for tp in xrange(1,nbrLines):
              tpl = geo.getPartAt(tp) # Next part (at index tp)

              # Needs to be an FMELine
              if type(tpl) == fmeobjects.FMEArc:
                  tpl = tpl.getAsLine()

              polygonBoundary.appendLine(tpl)

          return polygonBoundary

      # #################################################################
      # FeatureProcessor
      # #################################################################
      class FeatureProcessor(object):
          def __init__(self):
              self.omrade = []
              self.grans = []

          # Saving in different lists depending on if the feature is a gräns or område
          def input(self,feature):
              if feature.hasGeometry():
                  self.grans.append(feature)
              else:
                  self.omrade.append(feature)

          def close(self):

              # Iterating over all Områden sent to the PythonCaller
              for omr in self.omrade:
                  boundaryList = []
                  tempGrans = True # Will stop the loop after last item is found (temp = None)
                  index = 0 # Index of "Gräns"
                  innerIndex = 0 # For keeping track of holes
                  firstLine = True # If first line segment of a gräns

                  #Looping over all "gränser" in current "Område"
                  while tempGrans != None:
                      tempGrans = omr.getAttribute('childList{%i}.xml_parent_child_pos' % (index))

                      # Already found last "gräns" of the "område"
                      if not tempGrans:
                          break
                      tempGrans = int(tempGrans)

                      if not tempGrans == index: # To break in case something is wrong wth indices
                          print 'Index not correct'
                          break

                      # Retreiving the next segment and finding direction.
                      minusTest = omr.getAttribute('childList{%i}.minus.href' % (index))
                      if minusTest != None:
                          minus = True
                          tempGransID = minusTest
                      else:
                          minus = False
                          tempGransID = omr.getAttribute('childList{%i}.plus.href' % (index))

                      # Building line
                      # This part is for the first "Gräns" either in the outer (index == 0) polygon or
                      # a hole (innerIndex >= 1)
                      if firstLine:
                          partOne = gransFinder(tempGransID, self.grans)
                          polygonBoundary = initialBoundaryLine(partOne)
                          firstLine = False
                          if minus:
                              polygonBoundary.reverse()


                      # From the second "gräns" in the list.
                      else:
                          polygonBoundaryParts = gransFinder(tempGransID, self.grans)

                          geo = polygonBoundaryParts.getGeometry()

                          nbrLines = geo.numParts()

                          tmpLine = geo.getPartAt(0)

                          if type(tmpLine) == fmeobjects.FMEArc:
                              tmpLine = tmpLine.getAsLine()

                          #Iterating over the of the parts in the FMEPath object
                          for tp in xrange(1,nbrLines):

                              tpl = geo.getPartAt(tp)

                              if type(tpl) == fmeobjects.FMEArc:
                                  tpl = tpl.getAsLine()

                              tmpLine.appendLine(tpl)

                          if minus:
                              tmpLine.reverse()

                          polygonBoundary.appendLine(tmpLine)

                      # True if a closed polygon is found.
                      if polygonBoundary.isClosed(False): # False => not considering 3D
                          firstLine = True # Next will be first line of an inner polygon (if existing)
                          innerIndex += 1 # Counting inner polygons
                          boundaryList.append(polygonBoundary) # Appending current polygon to list
                          polygonBoundary = None

                      index += 1

                  # Final part: Creating the polygons incl. holes if present
                  # Creating a polygon with the outer boundary by popping it from the list of ploygons
                  if boundaryList:
                      outerPoly = fmeobjects.FMEDonut(boundaryList.pop(0))
                      # Iterating over all inner polygons that were found (the ouoter is already removed above)
                      for omrPoly in boundaryList:
                          innerPoly = fmeobjects.FMEDonut(omrPoly)
                          outerPoly.addInnerBoundaryCurve(omrPoly)

                      omr.setGeometry(outerPoly)

                      self.pyoutput(omr)
    PYTHONSYMBOL = FeatureProcessor
    -> FeatureMerger_2 [REQUESTOR]
Note: Adding Geometries to bestämmelser
FeatureMerger_2
    ATTR_ACCUM_MODE = Merge Supplier
    ATTR_CONFLICT_RES = Use Requestor
    IGNORE_NULLS = No
    JOIN_KEYS = @Value(xml_parent_id) @Value(xml_id) AUTO
    MERGE_TYPE = Attributes and Geometry
    PROCESS_DUPS = NO
    REJECT_NULL_MISSING_KEYS = No
    SUPPLIERS_FIRST = No
    MERGED -> AttributeRemover_3
AttributeRemover_3
    LIST_ATTRS = childList{}
    REMOVE_ATTRS = xml_id,gml_id,xml_parent_child_pos,ID_join,plus.href,xml_matched_element,plus,minus.href,linje
    -> TestFilter
TestFilter
    DEFAULT_VALUE = <UNFILTERED>
    TEST_LIST = "BOOL_OP,OR,COMPOSITE_TEST,""""""<Unused>"""""",TEST_CLAUSE,CASE_INSENSITIVE_TEST @Value(anvandningsslag) CONTAINS _W_",Water,"BOOL_OP,OR,COMPOSITE_TEST,""""""<Unused>"""""",TEST_CLAUSE,CASE_INSENSITIVE_TEST @Value(anvandningsslag) CONTAINS gata",Gata,"BOOL_OP,OR,COMPOSITE_TEST,""""""<Unused>"""""",TEST_CLAUSE,TEST @Value(uuid) = 3b2de3e5-2ea1-4233-b48e-54f4c87a0a10",EntirePlan,"BOOL_OP,OR,COMPOSITE_TEST,""""""<Unused>"""""",TEST_CLAUSE,CASE_INSENSITIVE_TEST @Value(anvandningsslag) CONTAINS gang",Pedestrian_bike,"BOOL_OP,OR,COMPOSITE_TEST,""""""<Unused>"""""",TEST_CLAUSE,CASE_INSENSITIVE_TEST @Value(EgenskapsBestList{0}.bestammelsetyp) CONTAINS Prickmark",Prickmark,"BOOL_OP,OR,COMPOSITE_TEST,""""""<Unused>"""""",TEST_CLAUSE,CASE_INSENSITIVE_TEST @Value(anvandningsslag) CONTAINS Natur",Natur,"BOOL_OP,OR,COMPOSITE_TEST,""""""<Unused>"""""",TEST_CLAUSE,CASE_INSENSITIVE_TEST @Value(anvandningsslag) CONTAINS park",Park
    Water -> FeatureColorSetter_Water
    Gata -> FeatureColorSetter_gata
    EntirePlan -> FeatureColorSetter_EntirePlan
    Pedestrian_bike -> FeatureColorSetter_pedestrian_bike
    Prickmark -> FeatureColorSetter_prickmark
    Natur -> FeatureColorSetter_natur
    Park -> FeatureColorSetter_park
    <UNFILTERED> -> min_dist_building
FeatureColorSetter_Water
    FILL_COLOR = 0,0,1
    MODE = Fixed
    COLORED -> FeatureColorSetter_Water_Colored
FeatureColorSetter_Water_Colored: Inspector
FeatureColorSetter_gata
    COLOR = 0.666667,0.666667,0.498039
    FILL_COLOR = 0.196078,0.196078,0.145098
    MODE = Fixed
    COLORED -> FeatureColorSetter_gata_Colored
    COLORED -> Dissolver_7
FeatureColorSetter_gata_Colored: Inspector
Note: Merge road data to reduce overlap within the dataset
Dissolver_7
    ACCUM_INPUT_ATTRS = Use Attributes From One Feature
    CLEANING_TOLERANCE = None
    CONNECT_Z_MODE = First Wins
    DEAGGREGATE_INPUT = Yes
    NO_OVRLP = No
    AREA -> Generalizer_2
Note: Eliminate extra points
Generalizer_2
    ALG_TEXT = Douglas (Generalize)
    CLEANING_TOLERANCE = None
    PRESERVE = Yes
    PRESERVE_PATHS = Yes
    TOLERANCE = 0.005
    -> LineIntersectBuffer_2 [Road]
FeatureColorSetter_EntirePlan
    COLOR = 0.666667,0,0
    MODE = Fixed
    COLORED -> FeatureColorSetter_EntirePlan_Colored
FeatureColorSetter_EntirePlan_Colored: Inspector
FeatureColorSetter_pedestrian_bike
    COLOR = 0.666667,0.666667,0.498039
    FILL_COLOR = 0.372549,0.372549,0.278431
    MODE = Fixed
    COLORED -> FeatureColorSetter_pedestrian_bike_Colored
FeatureColorSetter_pedestrian_bike_Colored: Inspector
FeatureColorSetter_prickmark
    COLOR = 0,0,0
    FILL_COLOR = 1,0.333333,0
    MODE = Fixed
    COLORED -> FeatureColorSetter_prickmark__Rejected_
FeatureColorSetter_prickmark__Rejected_: Inspector
FeatureColorSetter_natur
    COLOR = 0,0.666667,0
    FILL_COLOR = 0,0.666667,0
    MODE = Fixed
    COLORED -> FeatureColorSetter_natur_Colored
FeatureColorSetter_natur_Colored: Inspector
FeatureColorSetter_park
    COLOR = 0,1,0
    FILL_COLOR = 0,1,0
    MODE = Fixed
    COLORED -> FeatureColorSetter_park_Colored
FeatureColorSetter_park_Colored: Inspector
min_dist_building: AttributeCreator
    ATTR_TABLE:
      SET_TO min_dist = $(min_dist)
      SET_TO yo = $(min_dist)
    -> FeatureColorSetter_others
FeatureColorSetter_others
    COLOR = 0,0,0
    FILL_COLOR = 1,1,0.498039
    MODE = Fixed
    COLORED -> FeatureColorSetter_others_Colored
    COLORED -> AttributeCreator_3 [off]
    COLORED -> MinDistance [SpatialFilter_Candidate]
Note: Add minimum distance requirement
AttributeCreator_3
    ATTR_TABLE = SET_TO Min_Dist = 4.5
FeatureColorSetter_others_Colored: Inspector
MinDistance
    MIN_DIST = @Value(min_dist)
    SpatialFilter3 -> LineIntersectBuffer_2 [Polygon]
    SpatialFilter3 -> LineIntersectBuffer_2 [Clipper_3_Clipper]
    Tester_2_Passed -> Chopper_4
    Tester_2_Failed -> Chopper
    Tester_2_Failed -> Clipper_3 [CLIPPER]
Note: If testpasses, convert the polygon into individual lines
Chopper_4
    DEAGGREGATE_INPUT = Deaggregate
    MAX_VERTICES = 2
    MODE = By Vertex
    REMNANT_ATTR = _remnant
    CHOPPED -> LinesOk_2
Note: Green if lines are according to standard
LinesOk_2: FeatureColorSetter
    COLOR = 0,0.666667,0
    MODE = Fixed
    COLORED -> LinesOk_2_Colored
LinesOk_2_Colored: Inspector
Note: If test failes, convert the polygon into individual lines
Chopper
    DEAGGREGATE_INPUT = Deaggregate
    MAX_VERTICES = 2
    MODE = By Vertex
    REMNANT_ATTR = _remnant
    CHOPPED -> NeighborFinder_2 [BASE]
Note: Finds the lines that do not meet the minimum distance requirement.
NeighborFinder_2
    CANDIDATES_FIRST = No
    INSERT_VERTEX = No
    MAX = $(min_dist)
    MEASURES_FROM_CANDIDATE = Yes
    MEASURE_TYPE = Continuous
    MODE = Bases and Candidates
    TREAT_POLYGON_AS = Lines
    MATCHED -> AttributeCreator_4
    UNMATCHED_BASE -> LinesOk
Note: Calculate how many meters to move the house to make it acceptable for minimum distance requirement.
AttributeCreator_4
    ATTR_TABLE = SET_TO Dist_to_move = @Evaluate(@sub(@Value(min_dist),@Value(_distance)))
    -> LineNotOk
Note: Red if line(s) are NOT according to standard
LineNotOk: FeatureColorSetter
    COLOR = 0.666667,0,0
    MODE = Fixed
    COLORED -> LineNotOk_Colored
    COLORED -> Bufferer_2
LineNotOk_Colored: Inspector
Note: Create a buffer so it is easier to visualize why the house distance is not according to standard.
Bufferer_2
    ANGLE = 22.5
    CAP_STYLE = None
    CORNER_STYLE = Round
    MODE = AREA
    OFFSET = $(min_dist)
    BUFFERED -> Clipper_3 [CLIPPEE]
Note: buffer should only extend to property area
Clipper_3
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> Buffer_color
Buffer_color: FeatureColorSetter
    COLOR = 1,0,0
    FILL_COLOR = 1,0.666667,0.67451
    MODE = Fixed
    COLORED -> Buffer_color_Colored
Buffer_color_Colored: Inspector
Note: Green if lines are according to standard
LinesOk: FeatureColorSetter
    COLOR = 0,0.666667,0
    MODE = Fixed
    COLORED -> LinesOk_Colored
LinesOk_Colored: Inspector
LineIntersectBuffer_2
    Chopper_5_Chopped -> HouseIntersection [Roadlines]
    Chopper_5_Chopped -> RectangleCreater [RoadLines]
    Chopper_5_Untouched -> HouseIntersection [Roadlines]
    Chopper_5_Untouched -> RectangleCreater [RoadLines]
    Clipped_buffer -> RectangleCreater [Polygons]
Note: CUSTOME TRANSFORMER
RectangleCreater
    UNIQUEID = @Value(UniqueID)
    Rectangles -> VertexCounter
Note: check if polygons are rectangle or triangle
VertexCounter
    CNT_ATTR = _coordcount
    -> Tester_8
    -> Tester_14
Note: coorcount >= 5 is rectangle, suitable for parking
Tester_14
    BOOL_OP = OR
    TEST_CLAUSE = TEST @Value(_coordcount) >= 5
    PASSED -> SpatialFilter_5 [Candidate]
Note: Is the house and potential parking space disjoint? If yes, then make sure the area is rectangle
SpatialFilter_5
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = DISJOINT
    USE_BOUNDING_BOX = No
    PASSED -> Cal_length [LengthCalculator_2_Input]
    FAILED -> AreaGapAndOverlapCleaner_2
    FAILED -> AreaOnAreaOverlayer_3 [AREA] [off]
    <REJECTED> -> SpatialFilter_5__Rejected_
Cal_length
    UNIQUEID = @Value(UniqueID)
    _COORDCOUNT = @Value(_coordcount)
    Yes_Park -> YesPark_3
    No_Park -> NoPark_3
YesPark_3: Inspector
NoPark_3: Inspector
SpatialFilter_5__Rejected_: Inspector
AreaGapAndOverlapCleaner_2
    CLEANING_TOLERANCE = 0.0001
    CONNECT_Z_MODE = First Wins
    DEAGGREGATE_INPUT = YES
    FILL_ALL_GAPS = Yes
    MEASURE_TYPE = Continuous
    MISSING_VAL_MODE = Compute
    REPAIR_METHOD = Longest Boundary
    REPAIRED -> Dissolver_2
Note: Combine tiny polygons created by unnecessary nodes
Dissolver_2
    ACCUM_INPUT_ATTRS = Use Attributes From One Feature
    CLEANING_TOLERANCE = None
    CONNECT_Z_MODE = First Wins
    DEAGGREGATE_INPUT = Yes
    NO_OVRLP = No
    AREA -> Clipper_2 [CLIPPEE]
    AREA -> HouseIntersection [PolygonCutter_Polygons_1]
Clipper_2
    BOUNDARY_CASES = Treat as Inside
    CLEANING_TOLERANCE = None
    CLIPPED_ATTR = _clipped
    CLIP_TYPE = Multiple Clippers
    CREATE_AGGREGATES = Yes
    LINES_AS_SEGMENTS = No
    MEASURE_TYPE = Continuous
    MISSING_VAL_MODE = Compute
    PRESERVE_CLIPPEE_EXTENTS = No
    VAL_SOURCE = Clippee Only
    INSIDE -> Chopper_2
HouseIntersection
    UNIQUEID = @Value(UniqueID)
    _CLIPPED = @Value(_clipped)
    _COORDCOUNT = @Value(_coordcount)
    _OVERLAPS = @Value(_overlaps)
    _REMNANT = @Value(_remnant)
    PolygonCutter_Cut_1 -> SpatialFilter_4 [Candidate]
Note: Find the polygons that intersects the house
SpatialFilter_4
    AGGREGATE_HANDLING = Yes
    BASE_TYPE = Single Filter
    CURVE_BOUNDARY_RULE_PARAM = Default Rule
    PASS_CRITERIA = Pass Against One Filter
    PREDATTR = _predicate
    PREDICATES = INTERSECTS
    USE_BOUNDING_BOX = No
    PASSED -> Dissolver
    FAILED -> SpatialFilter_9 [Filter]
    FAILED -> SpatialFilter_9 [Candidate]
    FAILED -> Cal_length_3 [LengthCalculator_2_Input]
Note: Dissolve these polygons into one big polygon
Dissolver
    ACCUM_INPUT_ATTRS = Use Attributes From One Feature
    CLEANING_TOLERANCE = None
    CONNECT_Z_MODE = First Wins
    DEAGGREGATE_INPUT = Yes
    GROUP_BY = UniqueID
    NO_OVRLP = No
    AREA -> NoPark_2
Note: Since the house is there, there is no space for parking. Mark as red.
NoPark_2: FeatureColorSetter
    COLOR = 0.666667,0,0
    FILL_COLOR = 1,0,0.498039
    MODE = Fixed
    COLORED -> NO_Space_for_parking
Note: Add message in the attribute table
NO_Space_for_parking: AttributeCreator
    ATTR_TABLE = SET_TO Parking = There is no space for parking
    -> NoPark_2_Colored
NoPark_2_Colored: Inspector
Cal_length_3
    UNIQUEID = @Value(UniqueID)
    _COORDCOUNT = @Value(_coordcount)
    Yes_Park -> YesPark
    No_Park -> NoPark
YesPark: Inspector
NoPark: Inspector
Note: Check if there are tiny polygons next to each other, as a way to check for unnecessary nodes
SpatialFilter_9
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = TOUCHES
    USE_BOUNDING_BOX = No
    PASSED -> Dissolver_3
Note: Combine tiny polygons created by unnecessary nodes
Dissolver_3
    ACCUM_INPUT_ATTRS = Use Attributes From One Feature
    CLEANING_TOLERANCE = None
    CONNECT_Z_MODE = First Wins
    DEAGGREGATE_INPUT = Yes
    NO_OVRLP = No
    AREA -> Cal_length_5 [LengthCalculator_2_Input]
Cal_length_5
    UNIQUEID = @Value(UniqueID)
    _COORDCOUNT = @Value(_coordcount)
    Yes_Park -> YesPark_5
    No_Park -> NoPark_7
YesPark_5: Inspector
NoPark_7: Inspector
Note: coodcount = 4 is triangle, not suitable for parking
Tester_8
    BOOL_OP = OR
    TEST_CLAUSE = TEST @Value(_coordcount) = 4
    PASSED -> NoPark_4
Note: Triangle is not suitable for parking, mark as red.
NoPark_4: FeatureColorSetter
    COLOR = 0.666667,0,0
    FILL_COLOR = 1,0,0.498039
    MODE = Fixed
    COLORED -> NoPark_4_Colored
NoPark_4_Colored: Inspector

Bookmark: Detaljplan from GML-reader
DP_Grans (reader GML_1)
    attributes: typ{} xml_char(5), linje xml_geometry
    -> CsmapReprojector_5
DP_Planbestammelse (reader GML_1)
    attributes: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
DP_Egenskapsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> CsmapReprojector_3
DP_Plan (reader GML_1)
    attributes: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
DP_Omrade (reader GML_1)
    attributes: plus.nilReason xml_buffer, plus.gml_remoteSchema xml_buffer, plus.xlink_href xml_buffer, plus.xlink_title xml_buffer, plus.owns xml_boolean, minus.nilReason xml_buffer, minus.gml_remoteSchema xml_buffer, minus.xlink_href xml_buffer, minus.xlink_title xml_buffer, minus.owns xml_boolean
    -> CsmapReprojector_4
DP_Data (reader GML_1)
    attributes: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
DP_Anvandningsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, anvandningsslag xml_buffer, precisering xml_buffer, huvudsaklig xml_boolean, egenskapsbestammelse{}.nilReason xml_buffer, egenskapsbestammelse{}.gml_remoteSchema xml_buffer, egenskapsbestammelse{}.xlink_href xml_buffer, egenskapsbestammelse{}.xlink_title xml_buffer, egenskapsbestammelse{}.owns xml_boolean, administrativBestammelse{}.nilReason xml_buffer, administrativBestammelse{}.gml_remoteSchema xml_buffer, administrativBestammelse{}.xlink_href xml_buffer, administrativBestammelse{}.xlink_title xml_buffer, administrativBestammelse{}.owns xml_boolean
    -> CsmapReprojector_6
DP_AdministrativBestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> CsmapReprojector_7

Bookmark: Detaljplan (DP_Område) from XML-reader
DP_Omrade (reader XML_1)
    attributes: DP_Omrade.id xml_char(3), minus xml_char(1), minus.href xml_char(6), minus{} xml_char(1), minus{}.href xml_char(6), plus xml_char(1), plus.href xml_char(6), plus{} xml_char(1), plus{}.href xml_char(6), xml_fragment xml_xml, xml_id xml_char(21), xml_matched_element xml_char(10), xml_parent_child_pos xml_char(1), xml_parent_id xml_char(1)
    -> FeatureMerger [SUPPLIER]
minus (reader XML_1)
    attributes: minus xml_char(1), minus.href xml_char(6), xml_fragment xml_xml, xml_id xml_char(20), xml_matched_element xml_char(6), xml_parent_child_pos xml_decimal(3,0), xml_parent_id xml_char(21)
    -> Aggregator
plus (reader XML_1)
    attributes: plus xml_char(1), plus.href xml_char(6), xml_fragment xml_xml, xml_id xml_char(19), xml_matched_element xml_char(5), xml_parent_child_pos xml_decimal(3,0), xml_parent_id xml_char(21)
    -> Aggregator

Bookmark: Connects bestämmelser to områden
FeatureMerger_Egenskap
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(ID_join) @Value(omrade.xlink_href) AUTO
    LIST_ATTRS_TO_INCLUDE = anmarkning bestammelseid bestammelsetyp beteckning giltighet ursprunglig uuid variabel{}.DP_VarArtal.namn variabel{}.DP_VarArtal.varde variabel{}.DP_VarDatum.namn variabel{}.DP_VarDatum.varde variabel{}.DP_VarDecimaltal.namn variabel{}.DP_VarDecimaltal.varde variabel{}.DP_VarHeltal.namn variabel{}.DP_VarHeltal.varde variabel{}.DP_VarKod.namn variabel{}.DP_VarKod.varde variabel{}.DP_VarLinje.namn variabel{}.DP_VarLinje.varde variabel{}.DP_VarPunkt.namn variabel{}.DP_VarPunkt.varde variabel{}.DP_VarText.namn variabel{}.DP_VarText.varde variabel{}.owns
    LIST_NAME = EgenskapsBestList
    MERGE_TYPE = Attributes Only
    PROCESS_DUPS = YES
    REJECT_NULL_MISSING_KEYS = No
    SUPPLIERS_FIRST = No
    MERGED -> FeatureMerger_Anvandning [REQUESTOR]
    UNMERGED_REQUESTOR -> FeatureMerger_Anvandning [REQUESTOR]
FeatureMerger_Anvandning
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(ID_join) @Value(omrade.xlink_href) AUTO
    LIST_ATTRS_TO_INCLUDE = anmarkning anvandningsslag bestammelseid beteckning giltighet ursprunglig uuid
    LIST_NAME = AnvandningsBestList
    MERGE_TYPE = Attributes Only
    PROCESS_DUPS = YES
    REJECT_NULL_MISSING_KEYS = No
    SUPPLIERS_FIRST = No
    MERGED -> FeatureMerger_Administrativ [REQUESTOR]
    UNMERGED_REQUESTOR -> FeatureMerger_Administrativ [REQUESTOR]
FeatureMerger_Administrativ
    ATTR_ACCUM_MODE = Merge Supplier
    ATTR_CONFLICT_RES = Use Requestor
    CLEANING_TOLERANCE = None
    CONNECT_Z_MODE = First Wins
    GEOM_TYPE = Build Polygons
    IGNORE_NULLS = No
    JOIN_KEYS = @Value(ID_join) @Value(omrade.xlink_href) AUTO
    LIST_ATTRS_TO_INCLUDE = anmarkning bestammelseid bestammelsetyp beteckning giltighet ursprunglig uuid variabel{}.DP_VarArtal.namn variabel{}.DP_VarArtal.varde variabel{}.DP_VarDatum.namn variabel{}.DP_VarDatum.varde variabel{}.DP_VarDecimaltal.namn variabel{}.DP_VarDecimaltal.varde variabel{}.DP_VarHeltal.namn variabel{}.DP_VarHeltal.varde variabel{}.DP_VarKod.namn variabel{}.DP_VarKod.varde variabel{}.DP_VarLinje.namn variabel{}.DP_VarLinje.varde variabel{}.DP_VarPunkt.namn variabel{}.DP_VarPunkt.varde variabel{}.DP_VarText.namn variabel{}.DP_VarText.varde variabel{}.owns
    LIST_NAME = AdministrativBestList
    MERGE_TYPE = Attributes Only
    PROCESS_DUPS = YES
    REJECT_NULL_MISSING_KEYS = No
    SUPPLIERS_FIRST = No
    MERGED -> AttributeRemover
    UNMERGED_REQUESTOR -> AttributeRemover

Bookmark: Min: Parking availability - step 2: If house intersects with potential parking space, check for available space left
Note: Find the area of intersection between house and buffer
AreaOnAreaOverlayer_3
    ACCUM_ATTRS_NAME = Use Attributes From One Feature
    CLEANING_TOLERANCE = None
    CONNECT_Z_MODE = First Wins
    DEAGGREGATE_INPUT = Yes
    OVC_ATTR = _overlaps
    AREA -> Tester_3 [off]
Note: Find the area of intersection between house and buffer
Tester_3
    BOOL_OP = OR
    TEST_CLAUSE = TEST @Value(_overlaps) = 2
    PASSED -> Chopper_2 [off]
    PASSED -> SpatialFilter_4 [Filter] [off]
Note: Retrieve all nodes/points of interection
Chopper_2
    DEAGGREGATE_INPUT = Deaggregate
    MAX_VERTICES = 1
    MODE = By Vertex
    REMNANT_ATTR = _remnant
    CHOPPED -> HouseIntersection [Vertices]

FME custom transformer MinDistance

Parameters:
- MIN_DIST = @Value(min_dist)   # Min Dist

SpatialFilter_Filter (input)
    -> SpatialFilter [Filter]
SpatialFilter_Candidate (input)
    -> SpatialFilter [Candidate]
Note: Checks if house is in an area where buildings are allowed
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = WITHIN
    USE_BOUNDING_BOX = No
    PASSED -> Generalizer
Note: Eliminate extra points
Generalizer
    ALG_TEXT = Douglas (Generalize)
    PRESERVE = No
    PRESERVE_PATHS = No
    TOLERANCE = 0.005
    -> NeighborFinder [BASE]
    -> SpatialFilter3 (output)
SpatialFilter3 (output)
NeighborFinder_Candidate (input)
    -> NeighborFinder [CANDIDATE]
Note: Checks minimum distance to boundaries
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> Tester_2
Note: Test minimum distance requirement with actual measured minimum distance.
Tester_2
    BOOL_OP = OR
    TEST_CLAUSE = TEST @Value(min_dist) < @Value(_distance)
    PASSED -> Tester_2_Passed (output)
    FAILED -> Tester_2_Failed (output)
Tester_2_Passed (output)
Tester_2_Failed (output)

FME custom transformer HouseIntersection

Parameters:
- UNIQUEID = @Value(UniqueID)   # UniqueID
- _CLIPPED = @Value(_clipped)   # Clipped
- _COORDCOUNT = @Value(_coordcount)   # Coordcount
- _OVERLAPS = @Value(_overlaps)   # Overlaps
- _REMNANT = @Value(_remnant)   # Remnant

Vertices (input)
    -> NeighborFinder_3 [BASE]
Roadlines (input)
    -> LineOnAreaOverlayer [LINE]
PolygonCutter_Polygons_1 (input)
    -> PolygonCutter [Polygons]
    -> LineOnAreaOverlayer [AREA]
LineOnAreaOverlayer
    ATTR_ACCUM_MODE = Merge Incoming
    ATTR_CONFLICT_RES = Use Original
    CLEANING_TOLERANCE = None
    DEAGGREGATE_INPUT = Yes
    OV_ATTR = _overlaps
    LINE -> NeighborFinder_3 [CANDIDATE]
NeighborFinder_3
    CANDIDATES_FIRST = No
    INSERT_VERTEX = No
    K = 1
    MEASURES_FROM_CANDIDATE = Yes
    MEASURE_TYPE = Continuous
    MODE = Bases and Candidates
    TREAT_POLYGON_AS = Lines
    MATCHED -> VertexCreator
VertexCreator
    MODE_NAME = Add Point
    XVAL = @Value(_closest_candidate_x)
    YVAL = @Value(_closest_candidate_y)
    -> LineExtender
LineExtender
    LEN = 5
    STRETCHED -> PolygonCutter [Lines]
Note: Cutes the big polygon using the perpendicular lines
PolygonCutter
    SNAP_TOLERANCE = 0
    _GROUP_BY = @Value(UniqueID)
    Cut -> PolygonCutter_Cut_1 (output)
PolygonCutter_Cut_1 (output)

FME custom transformer RectangleCreater

Parameters:
- UNIQUEID = @Value(UniqueID)   # UniqueID

RoadLines (input)
    -> NeighborFinder [CANDIDATE]
Polygons (input)
    -> VertexExtractor
    -> PolygonCutter_2 [Polygons]
VertexExtractor
    Point -> NeighborFinder [BASE]
NeighborFinder
    CANDIDATES_FIRST = No
    GROUP_BY = UniqueID
    INSERT_VERTEX = No
    K = 1
    MEASURES_FROM_CANDIDATE = Yes
    MEASURE_TYPE = Continuous
    MODE = Bases and Candidates
    TREAT_POLYGON_AS = Lines
    MATCHED -> Tester
Tester
    BOOL_OP = OR
    TEST_CLAUSE = TEST @Value(_distance) > 0
    PASSED -> VertexCreator
VertexCreator
    MODE_NAME = Add Point
    XVAL = @Value(_closest_candidate_x)
    YVAL = @Value(_closest_candidate_y)
    -> LineExtender
LineExtender
    LEN = 5.5
    STRETCHED -> PolygonCutter_2 [Lines]
PolygonCutter_2
    SNAP_TOLERANCE = 0
    _GROUP_BY = @Value(UniqueID)
    Cut -> Rectangles (output)
Rectangles (output)

FME custom transformer Cal_length

Parameters:
- _COORDCOUNT = @Value(_coordcount)   # Coordcount
- UNIQUEID = @Value(UniqueID)   # UniqueID

LengthCalculator_2_Input (input)
    -> LengthCalculator_2
Note: Calculate the perimeter of the polygon
LengthCalculator_2
    DIM = 2
    LEN_ATTR = _length
    MULT = 1
    -> AttributeCreator_5
Note: Perimeter -10 /2 is the width of the polygon
AttributeCreator_5
    ATTR_TABLE = SET_TO Width = @Evaluate((@Value(_length)-10)/2)
    -> Tester_13
    -> Tester_12
Note: Width > or = 2.5m becomes green
Tester_13
    BOOL_OP = OR
    TEST_CLAUSE = TEST @Value(Width) >= 2.5
    PASSED -> YesPark_2
Note: Green if area is ok
YesPark_2: FeatureColorSetter
    COLOR = 0,0.666667,0
    FILL_COLOR = 0.631373,1,0.662745
    MODE = Fixed
    COLORED -> Space_for_parking_2
Note: Add message in the attribute table
Space_for_parking_2: AttributeCreator
    ATTR_TABLE = SET_TO Parking = There is space for parking
    -> Yes_Park (output)
Yes_Park (output)
Note: Width < 2.5m becomes red
Tester_12
    BOOL_OP = OR
    TEST_CLAUSE = TEST @Value(Width) < 2.5
    PASSED -> NoPark_3
Note: Red if not ok for parking
NoPark_3: FeatureColorSetter
    COLOR = 0.666667,0,0
    FILL_COLOR = 1,0,0.498039
    MODE = Fixed
    COLORED -> No_Park (output)
No_Park (output)

FME custom transformer LineIntersectBuffer

Polygon (input)
    -> AreaGapAndOverlapCleaner_2
Road (input)
    -> AreaGapAndOverlapCleaner_2
AreaGapAndOverlapCleaner_2
    CLEANING_TOLERANCE = 0.001
    CONNECT_Z_MODE = First Wins
    DEAGGREGATE_INPUT = YES
    FILL_ALL_GAPS = No
    MEASURE_TYPE = Continuous
    MISSING_VAL_MODE = Compute
    REPAIR_METHOD = Longest Boundary
    REPAIRED -> GeometryCoercer
    REMNANTS -> GeometryCoercer
GeometryCoercer
    GQUERY:
      for $geom in //geometry
      where $geom/count(parent::geometry) = 0
      return number($geom/@fme_id)
    KIND = fme_line
    COERCED -> LineOnLineOverlayer [LINE]
Note: Find the linse that intersects between the road and property.
LineOnLineOverlayer
    ATTRS_ACCUM_MODE = Use Attributes From One Feature
    CLEANING_TOLERANCE = None
    DEAGGREGATE_INPUT = Yes
    GENERATE_LIST_DROP = NO
    LOG_LEVEL = Full
    OV_ATTR = _overlaps
    SEPARATE_COLLINEAR_SEGMENTS = No
    LINE -> Tester_4
Note: Find the linse that intersects between the road and property.
Tester_4
    BOOL_OP = OR
    TEST_CLAUSE = TEST @Value(_overlaps) = 2
    PASSED -> Chopper_5
Chopper_5
    DEAGGREGATE_INPUT = Deaggregate
    MAX_VERTICES = 2
    MODE = By Vertex
    REMNANT_ATTR = _remnant
    CHOPPED -> Counter
    UNTOUCHED -> Chopper_5_Untouched (output)
    UNTOUCHED -> Counter
Chopper_5_Untouched (output)
Counter
    CNT_ATTR = UniqueID
    DOMAIN = counter
    SCOPE = Global
    START = 1
    -> Chopper_5_Chopped (output)
    -> Bufferer_3
Chopper_5_Chopped (output)
Note: Create a 5m meter, this is potential parking space.
Bufferer_3
    ANGLE = 22.5
    CAP_STYLE = None
    CORNER_STYLE = Round
    MODE = AREA
    OFFSET = 5
    BUFFERED -> Clipper_3 [CLIPPEE]
Clipper_3_Clipper (input)
    -> Clipper_3 [CLIPPER]
Note: The 5m buffer should only extend to the propety area, not the road.
Clipper_3
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> Clipped_buffer (output)
Clipped_buffer (output)

FME custom transformer PolygonCutter
Cut polygons by lines. 
The input asks for polygons (areas and ellipses are excepted) and lines (lines and arcs are excepted). The polygons are cut and the original attributes are added to the cut polygons. 
There is a group by option in the parameters and vertices can be snapped using the Snapping Tolerance parameter. 
The transformer does not take overlapping areas into account. If areas are overlapping they will be cut into pieces. 
Version 2:
Added the export of unused lines through the unused port. These lines have the attribute _remnant added and is set to 'yes' if it intersects with an area and 'no' if not. Non-line features will not have the attribute.
Author:     lars de vries 
Company:        Omkeere
Phone:      +31 (0)6 - 191.777.82
E-mail:     larsdevries@omkeere.com
Website:        http://omkeere.com
DevVersion: 2017.0.1.0 (build 17288)

Parameters:
- SNAP_TOLERANCE = 0.001   # Snapping Tolerance
- _GROUP_BY =   # Group By

Polygons_-__SpatialRelator_Supplier: Junction
    -> Polygons_-__SpatialRelator_Supplier_Output_-__SpatialRelator_Supplier
Polygons_-__SpatialRelator_Supplier_Output_-__SpatialRelator_Supplier: Junction
    -> SpatialRelator [Supplier]
    -> Polygons_-__SpatialRelator_Supplier_Output_-__SpatialRelator_Supplier_Output_-__Matcher
Note: ///2017-07-07 LVR / Nog te ontwikkelen: / - Opties voor 3D: Voorkeur voor lijnen of vlakken / - Juiste wijze voor groeperen opnemen
Polygons_-__SpatialRelator_Supplier_Output_-__SpatialRelator_Supplier_Output_-__Matcher: Junction
    -> ChangeDetector [ORIGINAL]
gfPolygonFilter__UNFILTERED__-__MessageLogger_INPUT: Junction
    -> MessageLogger

Bookmark: R1 - Read features
Note: Get _group_by attribute for application in: / - LineBuilder / - Intersector / - AreaBuilder / - SpatialRelator / - Matcher
Polygons (input)
    -> gfPolygonFilter
    -> Polygons_-__SpatialRelator_Supplier
Lines (input)
    -> gfLineFilter

Bookmark: 01 - Filter lines and join if possible
Note: Check the geometry for being a polygon
gfPolygonFilter: GeometryFilter
    BREAK_AGG = No
    GEOM_PORT_NAMES = Area Ellipse
    AREA -> Intersector
    ELLIPSE -> Intersector
    <UNFILTERED> -> gfPolygonFilter__UNFILTERED__-__MessageLogger_INPUT
Note: Check the geometry for being a polygon
gfLineFilter: GeometryFilter
    BREAK_AGG = No
    GEOM_PORT_NAMES = Line Arc
    LINE -> Intersector
    ARC -> Intersector
    <UNFILTERED> -> gfPolygonFilter__UNFILTERED__-__MessageLogger_INPUT

Bookmark: 02 - Cut areas with lines
Note: Intersect all lines by _group_by
Intersector
    ATTRS_ACCUM_MODE = Use Attributes From One Feature
    DEAGGREGATE_INPUT = Yes
    DUPLICATE_Z_NODES = No
    GENERATE_LIST_DROP = NO
    GRP_BY = _group_by
    MEASURE_TYPE = Continuous
    OV_ATTR = _overlaps
    PERFORM_SELF_INTERSECTION = No
    SEG_ATTR = _segments
    SEPARATE_COLLINEAR_SEGMENTS = No
    INTERSECTED -> AreaBuilder
Note: Build new areas from intersected lines by _group_by
AreaBuilder
    ALLOW_CYCLES = No
    CHECK_CURVE_DIRECTION = No
    CONNECT_Z_MODE = First Wins
    CONSIDER_NODE_ELEVATION = no
    DONUT_CREATION = YES
    DROP_HOLES = No
    GROUP_BY = _group_by
    LINES_AS_SEGMENTS = No
    POLY_ACCUM_ATTRS_NAME = Use Attributes From One Feature
    SNAPTYPE_PARAM = Vertex Snapping
    SNAP_TOLERANCE = $(SNAP_TOLERANCE)
    AREA -> SpatialRelator [Requestor]
    AREA -> SpatialFilter [Filter]
    Incomplete -> SpatialFilter [Candidate]

Bookmark: 03 - Post proces properties
Note: Relate original attributes for areas that are contained within their original shape
SpatialRelator
    AGGREGATE_HANDLING = No
    ATTR_ACCUM_MODE = Only Use Supplier
    CALC_CARD = No
    CURVE_BOUNDARY_RULE_PARAM = Default Rule
    GROUP_BY = _group_by
    PREDICATES = WITHIN
    SUCCESS_ATTR = _related_candidates
    -> ChangeDetector [REVISED]
Note: Check features for changes
ChangeDetector
    BLANK_AND_MISSING_DIFFER = No
    LENIENT_MATCH = No
    MATCH = 2D
    MATCHATTRS = _group_by
    MATCH_STRATEGY = Match Selected Attributes
    UNCHANGED -> AttributeRemover
    ADDED -> AttributeRemover_2

Bookmark: 04.1 - Attribute cleaning
Note: Remove intermediate attributes
AttributeRemover
    REMOVE_ATTRS = _group_by,_related_candidates
    -> Untouched (output)
AttributeRemover_2
    REMOVE_ATTRS = _group_by,_related_candidates
    -> Cut (output)

Bookmark: W2 - Output features
  Output features through the Untouched port if features are identical as the input and through the Cut port if they are cut into smaller pieces
Untouched (output)
Cut (output)

Bookmark: 04 - Check unused lines for remnants
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AttributeCreator
    FAILED -> AttributeCreator_2
AttributeCreator
    ATTR_TABLE = SET_TO _remnant = yes
    -> AttributeCreator_2_OUTPUT_-__Unused
AttributeCreator_2
    ATTR_TABLE = SET_TO _remnant = no
    -> AttributeCreator_2_OUTPUT_-__Unused
AttributeCreator_2_OUTPUT_-__Unused: Junction
    -> Unused (output)

Bookmark: W1 - Incorrect geometry
  Log and output unexpected geometries as Unused.
MessageLogger
    LOGFEATS = Yes
    MAXCOORDS = 5
    MAXFEATS = 20
    MESSAGE = Geometries do not contain the expected geometry. Make sure that the same geometry in fed as the name of the input port. Result my not be as aspected
    TYPE = WARN
    -> Unused (output)
Unused (output)

FME custom transformer VertexExtractor
Extracts all vertices from input geometries and outputs them as 3D Points.
When a vertex is 2D Point, its Z value is set to the value which is given as a user parameter. If the Z value is not specified, 2D points will be returned.
Input Ports
Input is the data containing coordinates that you would like to turn into vertices. If the source feature is a donut polygon or an aggregate, then this transformer will decompose the feature into its components before breaking them up.
Additionally all point features receive the attributes _feature_number and _vertex_number which, in combination, are unique for every source feature and, respectively, its parts.
The _part_number indicates whether the resulting point was derived from a donut polygon or an aggregate. If a donut or an aggregate was the origin, the _part_number is 0 for the first part and 1 or greater for all other parts. The _part_number is 0 in case of simple features.
Note: If you don't need to know the part numbers, you can also use the Chopper transformer which comes with FME. Setting Maximum Vertices to 1 in the Chopper exposes feature vertices. 
    Output Ports
Output is the point(s) that were created from the transformer. Each resulting point inherits all attributes from its source feature.
    Parameters
When a vertex is 2D Point, its Z value is set to the value which is given as a user parameter. If the Z value is not specified, 2D points will be returned.

Parameters:
- DEFAULT_Z_VALUE =   # Z Value for 2D Point (optional)

Input (input)
    -> Deaggregator
Note: If input feature consists of aggregates, / split it into "simple" features
Deaggregator
    ATTR_ACCUM_MODE = Merge List Attributes
    ATTR_CONFLICT_RES = Use List Attribute Values
    EXPLODE_INSTANCES = No
    LIST_ATTR_MODE_LOOKUP = LEAN
    MODE = Flatten One Level
    PART_NUMBER_FIELD = _part_number
    SPLIT_COMPOSITES = Yes
    DEAGGREGATED -> Counter
Counter
    CNT_ATTR = _feature_number
    DOMAIN = counter
    SCOPE = Local
    START = 0
    -> CoordinateConcatenator
Note: Get concatenated coordinates string
CoordinateConcatenator
    COORDINATES_TO_INCLUDE_DIS = X Y Z
    COORD_ATTR = _coordinates
    COORD_DELIM = \
    ELEMENT_DELIM = ,
    PRECISION = Yes
    -> AttributeSplitter
Note: Split the concatenated coordinates string / to each coordinate and make a list of those
AttributeSplitter
    ATTR_NAME = _coordinates
    DELIMITER = \
    DROP_EMPTY_PARTS = No
    LIST_NAME = _coordinate
    TRIM_OPTION = Both
    -> DimensionExtractor
Note: Extracts dimension, 3 or 2
DimensionExtractor
    DIM_ATTR = _dimension
    -> GeometryRemover
Note: Remove all geometries to prevent / creating many copies of geometry objects / before exploding the coordinate list. / this is very important for the memory usage efficiency.
GeometryRemover
    -> ListExploder
Note: Explode the coordinate list / into every vertex coordinate
ListExploder
    ATTR_ACCUM_MODE = Merge Incoming List
    ATTR_CONFLICT_RES = Use Incoming List
    INDEX_ATTR = _element_index
    LIST_ATTR = _coordinate{}
    ELEMENTS -> AttributeSplitter_1
Note: Change each vertex coordinate / to list structure containing [x,y,(z)]
AttributeSplitter_1
    ATTR_NAME = _coordinate
    DELIMITER = ,
    DROP_EMPTY_PARTS = No
    LIST_NAME = _list
    TRIM_OPTION = Both
    -> TestFilter
Note: Divide the work flow according to the dimension / and expose the list elements i.e. x,y.(z)
TestFilter
    DEFAULT_VALUE = <UNFILTERED>
    TEST_LIST = TEST_CLAUSE,"TEST @Value(_dimension) = 3",TEST_LIST,"&_dimension,=,3",TEST_MODE,Automatic,BOOL_OP,OR,_dimension = 3,TEST_CLAUSE,"TEST @Value(_dimension) = 2",TEST_LIST,"&_dimension,=,2",TEST_MODE,Automatic,BOOL_OP,OR,_dimension = 2
    _dimension = 3 -> AttributeManager
    _dimension = 2 -> ParameterFetcher
Note: When the dimension is 2 and default z is set, / set default value to _list{2} i.e. z. / the default value is given as a parameter
ParameterFetcher
    ATTR_LIST = _list{2} {$(DEFAULT_Z_VALUE)}
    -> AttributeManager
AttributeManager
    ATTR_TABLE:
      REMOVE _dimension
      RENAME_SET_VALUE _element_index > _vertex_number
      RENAME_SET_VALUE _list{2} > _z
      RENAME_SET_VALUE _list{1} > _y
      RENAME_SET_VALUE _list{0} > _x
      REMOVE _coordinate
      REMOVE _coordinates
      REMOVE _list{}
    -> VertexCreator
Note: Finally, create point from x,y,z
VertexCreator
    MODE_NAME = Replace with Point
    XVAL = @Value(_x)
    YVAL = @Value(_y)
    ZVAL = @Value(_z)
    -> Point (output)
Point (output)
