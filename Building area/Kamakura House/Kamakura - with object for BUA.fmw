FME workspace Kamakura - with object for BUA.fmw
Title: Kamakura - med objekt för BYA

Parameters:
- SourceDataset_IFC = C:\Users\seuppp\Documents\Exjobb\EXJOBB\FME-skript\Husmodeller\IFC-filer från Martin\180301 - Kamakura House.ifc   # Source Industry Foundation Class (IFC) File(s)

Readers:
- IFC_1: IFC from $(SourceDataset_IFC)

IfcSpace (reader IFC_1)
    attributes: GlobalId char(22), Name string, Description string, ObjectType string, LongName string, CompositionType enumeration, InteriorOrExteriorSpace enumeration, ElevationWithFlooring real, Axis geometry, Body geometry, Box geometry, FootPrint geometry
    -> FootprintAreaCalculator_IfcSpace [IfcSpace_Input]
FootprintAreaCalculator_IfcSpace
    ATTRIBUTE = @Value(LongName)
    Object_name = Area
    FootprintArea_Output -> FootprintArea_Output
FootprintArea_Output: Inspector

FME custom transformer FootprintAreaCalculator_IfcSpace

Parameters:
- Object_name = Area   # Object name
- ATTRIBUTE = @Value(LongName)   # Attribute

IfcSpace_Input (input)
    -> Tester
Note: Sort out the right IfcSpace object
Tester
    BOOL_OP = OR
    TEST_DESCRIPTION = ""
    TEST_CLAUSE = TEST @Value(LongName) = $(Object_name)
    TEST_MODE = Automatic
    PASSED -> SurfaceFootprintReplacer
SurfaceFootprintReplacer
    OFFSET_Z = 0
    LIGHT_Y = 0
    LIGHT_X = 0
    LIGHT_Z = 1
    SHADOW_MODE = Overhead Shadow
    FOOTPRINT -> AreaCalculator
AreaCalculator
    MULT = 1/1000000
    AREA_ATTR = _area
    AREA_TYPE = Plane Area
    -> AttributeRounder
AttributeRounder
    PLACES = 1
    SRC_ATTRS = _area
    ROUND_TYPE = Nearest
    -> FootprintArea_Output (output)
FootprintArea_Output (output)
