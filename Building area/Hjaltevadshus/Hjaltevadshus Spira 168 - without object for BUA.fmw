FME workspace Hjaltevadshus Spira 168 - without object for BUA.fmw
Title: Hjältevadshus - utan objekt för BYA

Parameters:
- SourceDataset_IFC = E:\Josefine\EXJOBB\FME-skript\Husmodeller\Hjältevadshus\168\Spira 168 - Spv - IFC.ifc   # Source Industry Foundation Class (IFC) File(s)
- DestDataset_GML = E:\Josefine\Arbetsmaterial\Output filer\Spira168_BYA2.gml   # Destination Geography Markup Language (GML) File

Readers:
- IFC_1: IFC from $(SourceDataset_IFC) in XY-MM

Writers:
- GML_1: GML to $(DestDataset_GML) in SWEREF-99-18-00

Bookmark: Spira 168
IfcSlab (reader IFC_1)
    attributes: GlobalId char(22), Name string, Description string, ObjectType string, Tag string, PredefinedType enumeration, Axis geometry, Body geometry, Box geometry, FootPrint geometry
    -> FootprintAreaCalculator [Clipper_Max_3m_Input]
    -> FootprintAreaCalculator [IfSlab_Input]
    -> FootprintAreaCalculator [All_ListBasedFeatureMerger]
    -> FootprintAreaCalculator [Clipper_Max_5m_Input]
IfcBuildingStorey (reader IFC_1)
    attributes: GlobalId char(22), Name string, Description string, ObjectType string, LongName string, CompositionType enumeration, Elevation real, Axis geometry, Body geometry, Box geometry, FootPrint geometry
    -> Aggregator
Aggregator
    CONCAT_ATTRS = ifc_unique_id
    LIST_NAME = buildingStoreysID
    LIST_ATTRS_TO_INCLUDE = ifc_unique_id
    ORDERED = No
    SEP = ,
    MODE = Attributes Only
    ACCUM_ATTRS_NAME = Merge Incoming Attributes
    AGGREGATE -> FootprintAreaCalculator [BuildingStorey_AggregatedList]
IfcWallStandardCase (reader IFC_1)
    attributes: GlobalId char(22), Name string, Description string, ObjectType string, Tag string, Axis geometry, Body geometry, Box geometry, FootPrint geometry
    -> FootprintAreaCalculator [Clipper_Max_3m_Input]
    -> FootprintAreaCalculator [Clipper_BottomEdge_Input]
    -> FootprintAreaCalculator [All_ListBasedFeatureMerger]
    -> FootprintAreaCalculator [Clipper_Max_5m_Input]
IfcWall (reader IFC_1)
    attributes: GlobalId char(22), Name string, Description string, ObjectType string, Tag string, Axis geometry, Body geometry, Box geometry, FootPrint geometry
    -> FootprintAreaCalculator [Clipper_Max_3m_Input]
    -> FootprintAreaCalculator [Clipper_BottomEdge_Input]
    -> FootprintAreaCalculator [All_ListBasedFeatureMerger]
    -> FootprintAreaCalculator [Clipper_Max_5m_Input]
IfcRoof (reader IFC_1)
    attributes: GlobalId char(22), Name string, Description string, ObjectType string, Tag string, ShapeType enumeration, Axis geometry, Body geometry, Box geometry, FootPrint geometry
    -> FootprintAreaCalculator [Clipper_Max_3m_Input]
    -> FootprintAreaCalculator [All_ListBasedFeatureMerger]
    -> FootprintAreaCalculator [Clipper_Max_5m_Input]
FootprintAreaCalculator
    LONGNAME = @Value(LongName)
    ELEVATION = 0
    IFC_PARENT_UNIQUE_ID = @Value(ifc_parent_unique_id)
    IFC_PARENT_ID = @Value(ifc_parent_id)
    LIST_NAME = buildingStoreysID{}
    IFC_UNIQUE_ID = @Value(ifc_unique_id)
    NAME = @Value(Name)
    FootprintArea -> Extruder

Bookmark: -> GML
  Skapar en solid av BasisBYA med area som attribut, ändrar koordinater och koordinatssystem till Sweref 99-18-00 (som höganäs detaljplan) och exporterar som GML-fil.
Note: Temp 5m, alt senare beräknad höjd / för byggnaden
Extruder
    DISTANCE = 5000
    DIRECTION = Auto
    EXTRUDED -> Extruder_Extruded
    EXTRUDED -> SolidBuilder
Extruder_Extruded: Inspector
SolidBuilder
    GROUP_BY = _area
    DROP_HOLES = No
    HOLE_ATTR = _is_void
    SOLID -> SolidBuilder_Solid
    SOLID -> CsmapReprojector_2
SolidBuilder_Solid: Inspector
CsmapReprojector_2
    SOURCE = XY-MM
    VERTICAL_HANDLING = Heights are relative to the ellipsoid(s) or geocentric
    RASTER_CELL_SIZE = Preserve Cells
    DEST = SWEREF-99-18-00
    INTERPOLATION_TYPE_NAME = Nearest Neighbor
    REPROJECTED -> AttributeCreator_2
AttributeCreator_2
    ATTR_TABLE = SET_TO BYA_area = @Value(_area)
    -> Building (writer GML_1)
Building (writer GML_1)
    attributes: BYA_area xml_real32

FME custom transformer Building_Clipper

Parameters:
- IFC_PARENT_UNIQUE_ID = @Value(ifc_parent_unique_id)   # Ifc Parent Unique Id
- DISTANCE = 10   # Distance
- OFFSET_Z = 0   # Z" Elevation

Input (input)
    -> Deaggregator
    -> BoundsExtractor
    -> BoundingBoxAccumulator
    -> Input
BoundingBoxAccumulator
    SOURCE_SCALE = 1
    DESTINATION_SCALE = 1
    TOPFER_INDEX = No
    ATTR_NAME = _topferIndex
    ACCUM_ATTRS_NAME = Use Attributes From One Feature
    BOUNDING_BOX -> FeatureMerger [REQUESTOR]
BoundsExtractor
    YMIN = _ymin
    XMIN = _xmin
    XMAX = _xmax
    ZMAX = _zmax
    ZMIN = _zmin
    YMAX = _ymax
    -> ListBuilder
ListBuilder
    LIST_NAME = _list
    LIST_ATTRS_TO_INCLUDE = _zmin ifc_parent_unique_id
    GROUPS_ORDERED = No
    -> ListRangeExtractor
ListRangeExtractor
    SRC_LIST = _list{}._zmin
    MIN = _min
    MAX = _max
    -> FeatureMerger [SUPPLIER]
FeatureMerger
    PROCESS_DUPS = No
    REJECT_NULL_MISSING_KEYS = No
    ATTR_CONFLICT_RES = Use Requestor
    ATTR_ACCUM_MODE = Merge Supplier
    JOIN_KEYS = @Value(ifc_parent_unique_id) @Value(_list{0}.ifc_parent_unique_id) AUTO
    MERGE_TYPE = Attributes Only
    IGNORE_NULLS = No
    SUPPLIERS_FIRST = No
    MERGED -> SurfaceFootprintReplacer
SurfaceFootprintReplacer
    OFFSET_Z = $(OFFSET_Z)+@Value(_min)
    SHADOW_MODE = Overhead Shadow
    FOOTPRINT -> Extruder
Extruder
    DISTANCE = $(DISTANCE)
    DIRECTION = Vertical
    EXTRUDED -> Clipper_2 [CLIPPER]
    EXTRUDED -> Output_extruded (output)
Output_extruded (output)
Deaggregator
    SPLIT_COMPOSITES = No
    PART_NUMBER_FIELD = _part_number
    ID_ATTR = _hierarchy_id
    GEOM_NAME_FIELD = _geometry_name
    MODE = Flatten One Level
    CHILD_ID_ATTR = _hierarchy_child_id_list
    PARENT_ID_ATTR = _hierarchy_parent_id
    COPY_ATTR = Every Node
    EXPLODE_INSTANCES = No
    LIST_ATTR_MODE_LOOKUP = LEAN
    ID_SELECTION = ID and Parent ID
    DEAGGREGATED -> GeometryFilter
GeometryFilter
    GEOM_PORT_NAMES = Solid
    BREAK_AGG = No
    SOLID -> Clipper_2 [CLIPPEE]
Clipper_2
    BOUNDARY_CASES = Treat as Inside
    MEASURE_TYPE = Continuous
    CLIP_TYPE = Multiple Clippers
    LINES_AS_SEGMENTS = No
    PRESERVE_CLIPPEE_EXTENTS = No
    MISSING_VAL_MODE = Compute
    VAL_SOURCE = Clippee Only
    CLIPPED_ATTR = _clipped
    CREATE_AGGREGATES = Yes
    INSIDE -> Output_clipper (output)
    <REJECTED> -> Rejected (output)
Output_clipper (output)
Rejected (output)
Input: Inspector [off]

FME custom transformer MinZ

Input (input)
    -> AttributeCreator
AttributeCreator
    ATTR_TABLE = SET_TO _zminval
    -> BoundsExtractor
BoundsExtractor
    YMIN = _ymin
    XMIN = _xmin
    XMAX = _xmax
    ZMAX = _zmax
    ZMIN = _zmin
    YMAX = _ymax
    -> PythonCaller
PythonCaller
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    PYTHONSYMBOL = FeatureProcessor
    -> Output (output)
Output (output)

FME custom transformer PointCloudClipper

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    GROUP_BY = ifc_unique_id
    EXTRACT_RASTER_NODATA_NAME = No
    ATTRS_TO_PRESERVE = ifc_parent_unique_id,String
    SPACING = 20
    ACCUM_ATTRS_NAME = Yes
    -> Clipper_2 [CLIPPEE]
Clipper (input)
    -> Clipper_2 [CLIPPER]
Clipper_2
    BOUNDARY_CASES = Treat as Inside
    MEASURE_TYPE = Continuous
    CLIP_TYPE = Single Clipper
    LINES_AS_SEGMENTS = No
    PRESERVE_CLIPPEE_EXTENTS = No
    MISSING_VAL_MODE = Compute
    VAL_SOURCE = Clippee Only
    CLIPPED_ATTR = _clipped
    CREATE_AGGREGATES = Yes
    INSIDE -> PointCloudCoercer
    INSIDE -> Output_3D (output)
PointCloudCoercer
    CONVERT_TO_DISPLAY = Individual Points
    PART_NUMBER_ATTR_NAME = _part_number
    POINT_COMPONENTS_PRESERVE_DISPLAY = Attributes
    ACCUM_ATTRS_NAME = Yes
    COERCED -> 2DForcer
2DForcer
    2D -> HullAccumulator
HullAccumulator
    GROUP_BY = ifc_unique_id
    HULLTYPE_PARAM = Convex ()
    3DMODE_PARAM = 2D
    HULL -> Output_2D (output)
Output_2D (output)
Output_3D (output)

FME custom transformer FootprintAreaCalculator

Parameters:
- IFC_PARENT_UNIQUE_ID = @Value(ifc_parent_unique_id)   # Ifc Parent Unique Id
- IFC_UNIQUE_ID = @Value(ifc_unique_id)   # ifc_unique_id
- ELEVATION = @Value(Elevation)   # Elevation
- NAME = @Value(Name)   # Name
- IFC_PARENT_ID = @Value(ifc_parent_id)   # Ifc Parent Id
- LONGNAME = @Value(LongName)   # LongName
- LIST_NAME = buildingStoreysID{}   # "" List Attribute

All_ListBasedFeatureMerger (input)
    -> ListBasedFeatureMerger [SUPPLIER]
IfSlab_Input (input)
    -> StoreyIndexFinder [AttributeCreator_StoreyList_Input]
BuildingStorey_AggregatedList (input)
    -> ListElementCounter_4
Note: Klipper byggnaden för att kunna ta ut utkragande delar.
ListElementCounter_4
    LIST_NAME = $(LIST_NAME)
    CNT_ATTR = nbrStoreys
    -> StoreyIndexFinder [PythonCaller_2_Input]
Note: Hittar Slabs på "första våningen"
StoreyIndexFinder
    1 -> CreateBasisBYA [Input_storey]
Clipper_Max_3m_Input (input)
    -> Clipper_Max_3m_2
Clipper_Max_5m_Input (input)
    -> Clipper_Max_5m_3
Clipper_BottomEdge_Input (input)
    -> Clipper_BottomEdge_2
Note: Klipper nedesta biten av väggen
Clipper_BottomEdge_2: Building_Clipper
    OFFSET_Z = @Value(Elevation)
    IFC_PARENT_UNIQUE_ID = @Value(ifc_parent_unique_id)
    DISTANCE = 10
    Output_extruded -> PointCloudClipper [Clipper]
    Output_clipper -> CreateBasisBYA [Input_facade]
    Rejected -> PointCloudClipper [Wall]
Note: Hanterar väggelement som inte går att klippa i föregående transformer
PointCloudClipper
    IFC_PARENT_UNIQUE_ID = @Value(ifc_parent_unique_id)
    IFC_UNIQUE_ID = @Value(ifc_unique_id)
    Output_2D -> CreateBasisBYA [Input_pointCloud]
CreateBasisBYA
    IFC_UNIQUE_ID = @Value(ifc_unique_id)
    -> AttributeManager_2
    -> Protruding_Part [Bufferer_Input]
    -> CreateBasisBYA_Output
    -> SurfaceFootprintReplacer_3
CreateBasisBYA_Output: Inspector
SurfaceFootprintReplacer_3
    OFFSET_Z = 0
    SHADOW_MODE = Overhead Shadow
    FOOTPRINT -> Dissolver_2
AreaCalculator
    MULT = 1/1000000
    AREA_ATTR = _area
    AREA_TYPE = Plane Area
    -> AttributeRounder
Note: Avrunda till en decimal
AttributeRounder
    SRC_ATTRS = _area
    ROUND_TYPE = Nearest
    PLACES = 1
    -> AttributeKeeper_2
AttributeKeeper_2
    KEEP_ATTRS = _area
    -> AttributeKeeper_2_Output
    -> FootprintArea (output)
FootprintArea (output)
AttributeKeeper_2_Output: Inspector

Bookmark: Klipper byggnaden 0-3 m
Clipper_Max_3m_2: Building_Clipper
    OFFSET_Z = @Value(Elevation)
    IFC_PARENT_UNIQUE_ID = @Value(ifc_parent_unique_id)
    DISTANCE = 3000
    Output_extruded -> PointCloudClipper_5 [Clipper]
    Output_clipper -> Protruding_Part [Clipper_Byggnad]
    Rejected -> PointCloudClipper_5 [Wall]
PointCloudClipper_5
    IFC_PARENT_UNIQUE_ID = @Value(ifc_parent_unique_id)
    IFC_UNIQUE_ID = @Value(ifc_unique_id)
    Output_3D -> Protruding_Part [Clipper_Byggnad]

Bookmark: Klipper byggnaden 3-5 m
Clipper_Max_5m_3: Building_Clipper
    OFFSET_Z = @Value(Elevation)+3000
    IFC_PARENT_UNIQUE_ID = @Value(ifc_parent_unique_id)
    DISTANCE = 2000
    Output_extruded -> PointCloudClipper_6 [Clipper]
    Output_clipper -> Protruding_Part_2 [Clipper_Byggnad]
    Rejected -> PointCloudClipper_6 [Wall]
PointCloudClipper_6
    IFC_PARENT_UNIQUE_ID = @Value(ifc_parent_unique_id)
    IFC_UNIQUE_ID = @Value(ifc_unique_id)
    Output_3D -> Protruding_Part_2 [Clipper_Byggnad]

Bookmark: 0-3m, < 0,5m
Protruding_Part
    OFFSET = 500
    _ZMINVAL = @Value(_zminval)
    DISTANCE = 3000
    _ZMIN = @Value(_zmin)
    Output_Outside -> Utkragande_del_Output_Outside_2
    Output_Outside -> Aggregator
Utkragande_del_Output_Outside_2: Inspector

Bookmark: 3-5m, < 1,5m
Note: Flytta zmin +3000mm
AttributeManager_2
    ATTR_TABLE:
      SET_TO _zminval = @Value(_zminval)+3000
      SET_TO _zmin = @Value(_zmin)+3000
    -> Protruding_Part_2 [Bufferer_Input]
Protruding_Part_2
    OFFSET = 1500
    _ZMINVAL = @Value(_zminval)
    DISTANCE = 2000
    _ZMIN = @Value(_zmin)
    Output_Outside -> Utkragande_del_2_Output_Outside_2
    Output_Outside -> Aggregator
Utkragande_del_2_Output_Outside_2: Inspector

Bookmark: Utkragade delar
Note: Klipper de utkragande delarna (Output_Outside)
Aggregator
    CONCAT_ATTRS = ifc_unique_id
    LIST_NAME = ListName
    LIST_ATTRS_TO_INCLUDE = ifc_unique_id
    ORDERED = No
    SEP = ,
    MODE = Attributes Only
    ACCUM_ATTRS_NAME = Merge Incoming Attributes
    AGGREGATE -> ListElementCounter
ListElementCounter
    LIST_NAME = ListName{}
    CNT_ATTR = nbrStoreys
    -> ListBasedFeatureMerger [REQUESTOR]
Note: Hämtar hela utkragande objekt mha ifc_unique_id, projicerar och lägger samman men "BasisBYA"
ListBasedFeatureMerger
    PROCESS_DUPS = Yes
    REFERATTR = ListName{}.ifc_unique_id
    BUILD_INCOMPLETE = Merge Supplier Information
    GEOM_TYPE = Build Aggregates
    MERGE_TYPE = Geometry
    REFEEATTR = @Value(ifc_unique_id)
    MODE = AUTO
    MERGED -> SurfaceFootprintReplacer_2
SurfaceFootprintReplacer_2
    OFFSET_Z = 0
    SHADOW_MODE = Overhead Shadow
    FOOTPRINT -> Dissolver_2
Note: Beräkna BYA
Dissolver_2
    DEAGGREGATE_INPUT = Yes
    CONNECT_Z_MODE = First Wins
    ACCUM_INPUT_ATTRS = Use Attributes From One Feature
    NO_OVRLP = No
    AREA -> AreaCalculator

FME custom transformer CreateBasisBYA

Parameters:
- IFC_UNIQUE_ID = @Value(ifc_unique_id)   # Ifc Unique Id

Bookmark: BasisBYA
Input_storey (input)
    -> MinZ_2
MinZ_2
    -> SurfaceFootprintReplacer_3
SurfaceFootprintReplacer_3
    OFFSET_Z = @Value(_zminval)
    SHADOW_MODE = Overhead Shadow
    FOOTPRINT -> Dissolver_2
Input_pointCloud (input)
    -> MinZ
Input_facade (input)
    -> MinZ
MinZ
    -> SurfaceFootprintReplacer_2
SurfaceFootprintReplacer_2
    OFFSET_Z = @Value(_zminval)
    SHADOW_MODE = Overhead Shadow
    FOOTPRINT -> HullAccumulator
    <REJECTED> -> SurfaceFootprintReplacer_2__Rejected_
HullAccumulator
    DEFAULTZ = @Value(_zminval)
    GROUP_BY = ifc_unique_id _zminval
    HULLTYPE_PARAM = Convex ()
    3DMODE_PARAM = 3D
    HULL -> Dissolver_2
Dissolver_2
    DEAGGREGATE_INPUT = Yes
    CONNECT_Z_MODE = Extend
    ACCUM_INPUT_ATTRS = Merge Incoming Attributes
    NO_OVRLP = No
    AREA -> BoundsExtractor
BoundsExtractor
    YMIN = _ymin
    XMIN = _xmin
    XMAX = _xmax
    ZMAX = _zmax
    ZMIN = _zmin
    YMAX = _ymax
    -> SurfaceFootprintReplacer
SurfaceFootprintReplacer
    OFFSET_Z = @Value(_zmin)
    SHADOW_MODE = Overhead Shadow
    FOOTPRINT -> DonutHoleExtractor_2
DonutHoleExtractor_2
    DEAGGREGATE_INPUT = Yes
    OUTERSHELL -> Output (output)
Output (output)
SurfaceFootprintReplacer_2__Rejected_: Inspector [off]

Bookmark: Test1
Dissolver [off]
    DEAGGREGATE_INPUT = Yes
    CONNECT_Z_MODE = First Wins
    ACCUM_INPUT_ATTRS = Use Attributes From One Feature
    NO_OVRLP = No
    AREA -> DonutHoleExtractor [off]
    AREA -> Dissolver_Area [off]
    INTERIOR_LINE -> Dissolver_InteriorLine [off]
    <REJECTED> -> Dissolver__Rejected_ [off]
Dissolver_Area: Inspector [off]
DonutHoleExtractor [off]
    DEAGGREGATE_INPUT = Yes
    OUTERSHELL -> Aggregator [off]
Aggregator [off]
    AGGREGATE_TYPE = Homogeneous Collection (If Possible)
    ORDERED = No
    SEP = ,
    MODE = Geometry - Assemble One Level
    ACCUM_ATTRS_NAME = Use Attributes From One Feature
    AGGREGATE -> Aggregator_Aggregate [off]
Aggregator_Aggregate: Inspector [off]
Dissolver_InteriorLine: Inspector [off]
Dissolver__Rejected_: Inspector [off]

Bookmark: Test2
GeometryCoercer [off]
    KIND = fme_line
    GQUERY:
      for $geom in //geometry
      where $geom/count(parent::geometry) = 0
      return number($geom/@fme_id)
    COERCED -> Snapper_2 [off]
    UNTOUCHED -> Snapper_2 [off]
Snapper_2 [off]
    SNAPTYPE_PARAM = End Point Snapping
    EXTEND_LINES = NEVER
    TOLERANCE = 10
    SAVE_SHORT_LINES = No
    SNAPPED -> AreaBuilder [off]
    SNAPPED -> Snapper_2_Snapped [off]
    UNTOUCHED -> AreaBuilder [off]
    UNTOUCHED -> Snapper_2_Untouched [off]
AreaBuilder [off]
    ALLOW_CYCLES = No
    CHECK_CURVE_DIRECTION = No
    POLY_LIST_ATTRS_TO_INCLUDE_MODE = Selected Attributes
    LINES_AS_SEGMENTS = No
    CONNECT_Z_MODE = First Wins
    SNAPTYPE_PARAM = None
    DONUT_CREATION = Yes
    DROP_HOLES = No
    CONSIDER_NODE_ELEVATION = no
    SNAP_TOLERANCE = 0
    POLY_ACCUM_ATTRS_NAME = Use Attributes From One Feature
    AREA -> AreaAmalgamator [AREAS] [off]
    AREA -> AreaBuilder_Area [off]
AreaAmalgamator [off]
    MIN_HOLE_AREA = 100
    AMALG_MODE = Binary Amalgamation
    DISSOLVE_INPUT = Yes
    MAX_TRIANGLE_LENGTH = 10
    MAX_TRIANGLE_WIDTH = 10
    AMALGAMATED -> AreaAmalgamator_Amalgamated [off]
AreaAmalgamator_Amalgamated: Inspector [off]
AreaBuilder_Area: Inspector [off]
Snapper_2_Snapped: Inspector [off]
Snapper_2_Untouched: Inspector [off]
AreaOnAreaOverlayer [off]
    DEAGGREGATE_INPUT = Yes
    OVC_ATTR = _overlaps
    CONNECT_Z_MODE = First Wins
    ACCUM_ATTRS_NAME = Use Attributes From One Feature
    AREA -> AreaOnAreaOverlayer_Area [off]
    <REJECTED> -> AreaOnAreaOverlayer__Rejected_ [off]
AreaOnAreaOverlayer_Area: Inspector [off]
AreaOnAreaOverlayer__Rejected_: Inspector [off]

FME custom transformer Protruding_Part

Parameters:
- _ZMINVAL = @Value(_zminval)   # Zminval
- OFFSET = 500   # Buffer Amount
- DISTANCE = 3000   # Distance
- _ZMIN = @Value(_zmin)   # Zmin

Bufferer_Input (input)
    -> Bufferer
Clipper_Byggnad (input)
    -> Clipper [CLIPPEE]
Clipper
    BOUNDARY_CASES = Treat as Inside
    MEASURE_TYPE = Continuous
    ATTR_CONFLICT_RES = Use Clippee
    CLIP_TYPE = Multiple Clippers
    LINES_AS_SEGMENTS = No
    PRESERVE_CLIPPEE_EXTENTS = No
    ATTR_ACCUM_MODE = Merge Clipper
    CONNECT_Z_MODE = First Wins
    DEFAULT_VAL = 0
    MISSING_VAL_MODE = Compute
    VAL_SOURCE = Clippee Only
    CLIPPED_ATTR = _clipped
    CREATE_AGGREGATES = Yes
    INSIDE -> Output_Inside (output)
    OUTSIDE -> GeometryValidator
    <REJECTED> -> Clipper__Rejected_
Output_Inside (output)
Note: Kontrollera så att objekten har geometri
GeometryValidator
    SUMMARY = Detailed
    TYPE_REPAIR = TYPE_REPAIR
    PRESETS = Basic Geometry Integrity
    ARC_ENDPOINT_TOLERANCE_MODE = Auto
    ISSUE_ATTR_NAME = _issues
    ORIENTATION_CHECK_DIR = Valid
    CONNECT_Z_MODE_TR = First Wins
    NULL_REMOVAL = NULL_REMOVAL
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    NAN_REMOVAL = NAN_REMOVAL
    AREA_ORIENTATION = AREA_ORIENTATION
    REPAIR = Yes
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    CAP_STYLE = Round
    OFFSET = $(OFFSET)
    ANGLE = 1
    CORNER_STYLE = Round
    BUFFERED -> SurfaceFootprintReplacer
    BUFFERED -> Bufferer_Buffered
Bufferer_Buffered: Inspector [off]
SurfaceFootprintReplacer
    OFFSET_Z = @Value(_zmin)
    SHADOW_MODE = Overhead Shadow
    FOOTPRINT -> Extruder
Note: Extrude 3 el 2 m
Extruder
    DISTANCE = $(DISTANCE)
    DIRECTION = Auto
    EXTRUDED -> Extruder_Extruded
    EXTRUDED -> Clipper [CLIPPER]
    <REJECTED> -> Extruder__Rejected_
Extruder_Extruded: Inspector
Extruder__Rejected_: Inspector

FME custom transformer StoreyIndexFinder

Note: Transformer från workspace KTH_demohuse_walls_roof_openings släppt under 3-Clause BSD License. / Framtagandet är finansierat av: / Smart Built Environments Testbädd: Smarta plan-, bygg- och förvaltningsprocesser över hela livscykeln. / Projektet Får Jag Lov koordinerat av Boverket.
Note: Connect to UUID creator for the walls (or other feature)
AttributeCreator_StoreyList_Input (input)
    -> AttributeCreator_StoreyList
Note: Connect to ListElementCounter / belonging to IfcBuildingStorey
PythonCaller_2_Input (input)
    -> PythonCaller_2
1 (output)
2 (output)
0 (output)

Bookmark: Adding index per building storey
AttributeCreator_StoreyList
    ATTR_TABLE = SET_TO storeyListIndex
    -> PythonCaller_2
PythonCaller_2
    NEW_ATTRIBUTES = storeyListIndex
    PYTHONSOURCE:
      import fme
      import fmeobjects
      # Template Function interface:
      # When using this function, make sure its name is set as the value of
      # the 'Class or Function to Process Features' transformer parameter
      def processFeature(feature):
          pass


      def listFinder(f): # f - the list with all features
          pos = 0 # Index in list
          while pos < len(f):
              attList = f[pos].getAllAttributeNames() # get all feature attributes
              for att in attList:
                  if 'buildingStoreysID' in att:
                      return f[pos].getAttribute('buildingStoreysID{}.ifc_unique_id')
              pos += 1
          return None

      def storeyIndexFinder(fe,storeyList):
          # Returns the index in the storey list of current feature
          parentID = fe.getAttribute('ifc_parent_unique_id')
          pos = 0
          while pos < len(storeyList):
              if storeyList[pos] == parentID:
                  return pos
              else:
                  pass # Do nothing
              pos += 1

      # Template Class Interface:
      # When using this class, make sure its name is set as the value of
      # the 'Class or Function to Process Features' transformer parameter
      class FeatureProcessor(object):
          def __init__(self):
              self.featureList = []
              self.logger = fmeobjects.FMELogFile()
              # logger.logMessageString('message')

          def input(self,feature): # This function is called every time a feature is added
              self.featureList.append(feature)

          def close(self):
              li = listFinder(self.featureList) # Return a list with storey id
              for f in self.featureList:
                  currIndex = storeyIndexFinder(f, li) # Check feature parent_id against list with storey id
                  f.setAttribute("storeyListIndex", currIndex)
                  self.pyoutput(f)
    PYTHONSYMBOL = FeatureProcessor
    -> Tester_StoreyIndex [off]
    -> TestFilter
TestFilter
    TEST_LIST = BOOL_OP,OR,COMPOSITE_TEST,<Unused>,TEST_CLAUSE,"TEST @Value(storeyListIndex) = 1",1,BOOL_OP,OR,COMPOSITE_TEST,<Unused>,TEST_CLAUSE,"TEST @Value(storeyListIndex) = 2",2,BOOL_OP,OR,COMPOSITE_TEST,<Unused>,TEST_CLAUSE,"TEST @Value(storeyListIndex) = 0",0
    DEFAULT_VALUE = <UNFILTERED>
    1 -> 1 (output)
    2 -> 2 (output)
    0 -> 0 (output)

Bookmark: Tester from KTH_demohouse_..
Note: Which storey index to include
Tester_StoreyIndex [off]
    TEST_MODE = Automatic
    TEST_CLAUSE = TEST @Value(storeyListIndex) = 1
    BOOL_OP = OR
    TEST_DESCRIPTION = ""
