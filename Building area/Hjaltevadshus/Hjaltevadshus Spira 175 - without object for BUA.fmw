FME workspace Hjaltevadshus Spira 175 - without object for BUA.fmw

Parameters:
- SourceDataset_IFC_5 = E:\Josefine\EXJOBB\FME-skript\Husmodeller\Hjältevadshus\175\Spira 175 - Spv  - IFC.ifc   # Source Industry Foundation Class (IFC) File(s)

Readers:
- IFC_1: IFC from $(SourceDataset_IFC_5) in XY-MM

Bookmark: Spira 175
IfcSlab (reader IFC_1)
    attributes: GlobalId char(22), Name string, Description string, ObjectType string, Tag string, PredefinedType enumeration, Axis geometry, Body geometry, Box geometry, FootPrint geometry
    -> FootprintAreaCalculator [IfSlab_Input]
    -> FootprintAreaCalculator [All_ListBasedFeatureMerger]
    -> FootprintAreaCalculator [Clipper_Max_3m_Input]
    -> FootprintAreaCalculator [Clipper_Max_5m_Input]
IfcBuildingStorey (reader IFC_1)
    attributes: GlobalId char(22), Name string, Description string, ObjectType string, LongName string, CompositionType enumeration, Elevation real, Axis geometry, Body geometry, Box geometry, FootPrint geometry
    -> Aggregator_3
Aggregator_3
    LIST_NAME = buildingStoreysID
    LIST_ATTRS_TO_INCLUDE = ifc_unique_id
    CONCAT_ATTRS = ifc_unique_id
    ORDERED = No
    ACCUM_ATTRS_NAME = Merge Incoming Attributes
    MODE = Attributes Only
    SEP = ,
    AGGREGATE -> FootprintAreaCalculator [BuildingStorey_AggregatedList]
IfcWall (reader IFC_1)
    attributes: GlobalId char(22), Name string, Description string, ObjectType string, Tag string, Axis geometry, Body geometry, Box geometry, FootPrint geometry
    -> Tester
IfcWallStandardCase (reader IFC_1)
    attributes: GlobalId char(22), Name string, Description string, ObjectType string, Tag string, Axis geometry, Body geometry, Box geometry, FootPrint geometry
    -> Tester
Note: Remove a wall under the house
Tester
    TEST_MODE = Automatic
    BOOL_OP = OR
    TEST_CLAUSE = TEST @Value(ifc_unique_id) != 1w4KozkgnE5h9WFsZPGqIX_91216
    TEST_DESCRIPTION = ""
    PASSED -> FootprintAreaCalculator [Clipper_BottomEdge_Input]
    PASSED -> FootprintAreaCalculator [Clipper_Max_5m_Input]
    PASSED -> FootprintAreaCalculator [Clipper_Max_3m_Input]
    PASSED -> FootprintAreaCalculator [All_ListBasedFeatureMerger]
IfcRoof (reader IFC_1)
    attributes: GlobalId char(22), Name string, Description string, ObjectType string, Tag string, ShapeType enumeration, Axis geometry, Body geometry, Box geometry, FootPrint geometry
    -> IfcRoof_-__FootprintAreaCalculator_All_ListBasedFeatureMerger
IfcRoof_-__FootprintAreaCalculator_All_ListBasedFeatureMerger: Junction
    -> FootprintAreaCalculator [All_ListBasedFeatureMerger]
    -> FootprintAreaCalculator [Clipper_Max_3m_Input]
    -> FootprintAreaCalculator [Clipper_Max_5m_Input]
FootprintAreaCalculator
    ELEVATION = @Value(Elevation)
    NAME = @Value(Name)
    LIST_NAME = buildingStoreysID{}
    IFC_PARENT_UNIQUE_ID = @Value(ifc_parent_unique_id)
    IFC_UNIQUE_ID = @Value(ifc_unique_id)
    IFC_PARENT_ID = @Value(ifc_parent_id)
    LONGNAME = @Value(LongName)
    FootprintArea -> FootprintAreaCalculator_FootprintArea
FootprintAreaCalculator_FootprintArea: Inspector

Bookmark: -> GML
Note: Temp 5m, alt senare beräknad höjd / för byggnaden
Extruder_2 [off]
    DISTANCE = 5000
    DIRECTION = Auto
    EXTRUDED -> Extruder_Extruded_2 [off]
    EXTRUDED -> SolidBuilder_2 [off]
Extruder_Extruded_2: Inspector [off]
SolidBuilder_2 [off]
    DROP_HOLES = No
    HOLE_ATTR = _is_void
    GROUP_BY = _area
    SOLID -> SolidBuilder_Solid_2 [off]
    SOLID -> CsmapReprojector_3 [off]
SolidBuilder_Solid_2: Inspector [off]
CsmapReprojector_3 [off]
    DEST = SWEREF-99-18-00
    SOURCE = XY-MM
    RASTER_CELL_SIZE = Preserve Cells
    VERTICAL_HANDLING = Heights are relative to the ellipsoid(s) or geocentric
    INTERPOLATION_TYPE_NAME = Nearest Neighbor
    REPROJECTED -> AttributeCreator_3 [off]
AttributeCreator_3 [off]
    ATTR_TABLE = SET_TO BYA_area = @Value(_area)

FME custom transformer FootprintAreaCalculator

Parameters:
- IFC_PARENT_UNIQUE_ID = @Value(ifc_parent_unique_id)   # Ifc Parent Unique Id
- IFC_UNIQUE_ID = @Value(ifc_unique_id)   # ifc_unique_id
- ELEVATION = @Value(Elevation)   # Elevation
- NAME = @Value(Name)   # Name
- IFC_PARENT_ID = @Value(ifc_parent_id)   # Ifc Parent Id
- LONGNAME = @Value(LongName)   # LongName
- LIST_NAME = buildingStoreysID{}   # "" List Attribute

All_ListBasedFeatureMerger (input)
    -> ListBasedFeatureMerger [SUPPLIER]
IfSlab_Input (input)
    -> StoreyIndexFinder [AttributeCreator_StoreyList_Input]
BuildingStorey_AggregatedList (input)
    -> ListElementCounter_4
Note: Clip the building to be able to find the protruding parts.
ListElementCounter_4
    LIST_NAME = $(LIST_NAME)
    CNT_ATTR = nbrStoreys
    -> StoreyIndexFinder [PythonCaller_2_Input]
Note: Find Slabs on "first floor"
StoreyIndexFinder
    1 -> CreateBasisBYA [Input_storey]
Clipper_Max_3m_Input (input)
    -> Clipper_Max_3m_2
Clipper_Max_5m_Input (input)
    -> Clipper_Max_5m_3
Clipper_BottomEdge_Input (input)
    -> Clipper_BottomEdge_2
Note: Clip lowest part of the wall
Clipper_BottomEdge_2: Building_Clipper
    DISTANCE = 10
    IFC_PARENT_UNIQUE_ID = @Value(ifc_parent_unique_id)
    OFFSET_Z = @Value(Elevation)
    Output_extruded -> PointCloudClipper [Clipper]
    Output_clipper -> CreateBasisBYA [Input_facade]
    Rejected -> PointCloudClipper [Wall]
Note: Handle wall objects that won't clip with default FME Clipper
PointCloudClipper
    IFC_UNIQUE_ID = @Value(ifc_unique_id)
    IFC_PARENT_UNIQUE_ID = @Value(ifc_parent_unique_id)
    Output_2D -> CreateBasisBYA [Input_pointCloud]
CreateBasisBYA
    IFC_UNIQUE_ID = @Value(ifc_unique_id)
    -> AttributeManager_2
    -> Protruding_Part [Bufferer_Input]
    -> SurfaceFootprintReplacer_3
SurfaceFootprintReplacer_3
    SHADOW_MODE = Overhead Shadow
    OFFSET_Z = 0
    FOOTPRINT -> Snapper
Note: Calculate BUA, / scale from mm2 to m2
AreaCalculator
    MULT = 1/1000000
    AREA_ATTR = _area
    AREA_TYPE = Plane Area
    -> AttributeRounder
Note: Round to on dec.
AttributeRounder
    ROUND_TYPE = Nearest
    PLACES = 1
    SRC_ATTRS = _area
    -> AttributeKeeper_2
AttributeKeeper_2
    KEEP_ATTRS = _area
    -> FootprintArea (output)
FootprintArea (output)

Bookmark: Klipper byggnaden 0-3 m
Clipper_Max_3m_2: Building_Clipper
    DISTANCE = 3000
    IFC_PARENT_UNIQUE_ID = @Value(ifc_parent_unique_id)
    OFFSET_Z = @Value(Elevation)
    Output_extruded -> PointCloudClipper_5 [Clipper]
    Output_clipper -> Protruding_Part [Clipper_Byggnad]
    Rejected -> PointCloudClipper_5 [Wall]
PointCloudClipper_5
    IFC_UNIQUE_ID = @Value(ifc_unique_id)
    IFC_PARENT_UNIQUE_ID = @Value(ifc_parent_unique_id)
    Output_3D -> Protruding_Part [Clipper_Byggnad]

Bookmark: Klipper byggnaden 3-5 m
Clipper_Max_5m_3: Building_Clipper
    DISTANCE = 2000
    IFC_PARENT_UNIQUE_ID = @Value(ifc_parent_unique_id)
    OFFSET_Z = @Value(Elevation)+3000
    Output_extruded -> PointCloudClipper_6 [Clipper]
    Output_clipper -> Protruding_Part_2 [Clipper_Byggnad]
    Rejected -> PointCloudClipper_6 [Wall]
PointCloudClipper_6
    IFC_UNIQUE_ID = @Value(ifc_unique_id)
    IFC_PARENT_UNIQUE_ID = @Value(ifc_parent_unique_id)
    Output_3D -> Protruding_Part_2 [Clipper_Byggnad]

Bookmark: 0-3m, < 0,5m
Protruding_Part
    _ZMIN = @Value(_zmin)
    DISTANCE = 3000
    _ZMINVAL = @Value(_zminval)
    OFFSET = 500
    Output_Outside -> Aggregator

Bookmark: 3-5m, < 1,5m
Note: Flytta zmin +3000mm
AttributeManager_2
    ATTR_TABLE:
      SET_TO _zminval = @Value(_zminval)+3000
      SET_TO _zmin = @Value(_zmin)+3000
    -> Protruding_Part_2 [Bufferer_Input]
Protruding_Part_2
    _ZMIN = @Value(_zmin)
    DISTANCE = 2000
    _ZMINVAL = @Value(_zminval)
    OFFSET = 1500
    Output_Outside -> Aggregator

Bookmark: Protruding parts
Note: Clip protruding parts (Output_Outside)
Aggregator
    LIST_NAME = ListName
    LIST_ATTRS_TO_INCLUDE = ifc_unique_id
    CONCAT_ATTRS = ifc_unique_id
    ORDERED = No
    ACCUM_ATTRS_NAME = Merge Incoming Attributes
    MODE = Attributes Only
    SEP = ,
    AGGREGATE -> ListElementCounter
ListElementCounter
    LIST_NAME = ListName{}
    CNT_ATTR = nbrStoreys
    -> ListBasedFeatureMerger [REQUESTOR]
Note: Retrive the whole protruding object with ifc_unique_id, project and merge with "BasisBUA"
ListBasedFeatureMerger
    MERGE_TYPE = Geometry
    BUILD_INCOMPLETE = Merge Supplier Information
    GEOM_TYPE = Build Aggregates
    MODE = AUTO
    REFEEATTR = @Value(ifc_unique_id)
    REFERATTR = ListName{}.ifc_unique_id
    PROCESS_DUPS = Yes
    MERGED -> SurfaceFootprintReplacer_2
SurfaceFootprintReplacer_2
    SHADOW_MODE = Overhead Shadow
    OFFSET_Z = 0
    FOOTPRINT -> Snapper
Dissolver_2
    DEAGGREGATE_INPUT = Yes
    NO_OVRLP = No
    CONNECT_Z_MODE = First Wins
    ACCUM_INPUT_ATTRS = Use Attributes From One Feature
    AREA -> AreaCalculator

Bookmark: Prepare for dissolve
  Snapp areas that won't dissolve (because they don't intersect/ are connected)
Snapper
    SNAPTYPE_PARAM = Segment Snapping
    CLEANING_TOLERANCE_MODE = AUTO
    TOLERANCE = 10
    SNAPPED -> Dissolver_2
    UNTOUCHED -> Dissolver_2

FME custom transformer CreateBasisBYA

Parameters:
- IFC_UNIQUE_ID = @Value(ifc_unique_id)   # Ifc Unique Id

Bookmark: BasisBYA
Input_storey (input)
    -> MinZ_2
MinZ_2
    -> SurfaceFootprintReplacer_3
SurfaceFootprintReplacer_3
    SHADOW_MODE = Overhead Shadow
    OFFSET_Z = @Value(_zminval)
    FOOTPRINT -> Snapper
Input_pointCloud (input)
    -> MinZ
Input_facade (input)
    -> MinZ
MinZ
    -> SurfaceFootprintReplacer_2
SurfaceFootprintReplacer_2
    SHADOW_MODE = Overhead Shadow
    OFFSET_Z = @Value(_zminval)
    FOOTPRINT -> HullAccumulator
    <REJECTED> -> SurfaceFootprintReplacer_2__Rejected_
HullAccumulator
    DEFAULTZ = @Value(_zminval)
    HULLTYPE_PARAM = Convex ()
    3DMODE_PARAM = 3D
    GROUP_BY = ifc_unique_id _zminval
    HULL -> Snapper
Dissolver_2
    DEAGGREGATE_INPUT = Yes
    NO_OVRLP = No
    CONNECT_Z_MODE = Extend
    ACCUM_INPUT_ATTRS = Merge Incoming Attributes
    AREA -> BoundsExtractor
BoundsExtractor
    ZMIN = _zmin
    ZMAX = _zmax
    XMAX = _xmax
    YMIN = _ymin
    YMAX = _ymax
    XMIN = _xmin
    -> SurfaceFootprintReplacer
SurfaceFootprintReplacer
    SHADOW_MODE = Overhead Shadow
    OFFSET_Z = @Value(_zmin)
    FOOTPRINT -> DonutHoleExtractor_2
DonutHoleExtractor_2
    DEAGGREGATE_INPUT = Yes
    OUTERSHELL -> Output (output)
Output (output)
SurfaceFootprintReplacer_2__Rejected_: Inspector [off]

Bookmark: Prepare for dissolve
  Snapp areas that won't dissolve (because they don't intersect/ are connected)
Snapper
    SNAPTYPE_PARAM = Segment Snapping
    CLEANING_TOLERANCE_MODE = AUTO
    TOLERANCE = 10
    SNAPPED -> Dissolver_2
    UNTOUCHED -> Dissolver_2

FME custom transformer MinZ_3

Input (input)
    -> AttributeCreator
AttributeCreator
    ATTR_TABLE = SET_TO _zminval
    -> BoundsExtractor
BoundsExtractor
    ZMIN = _zmin
    ZMAX = _zmax
    XMAX = _xmax
    YMIN = _ymin
    YMAX = _ymax
    XMIN = _xmin
    -> PythonCaller
PythonCaller
    PYTHONSYMBOL = FeatureProcessor
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    -> Output (output)
Output (output)

FME custom transformer StoreyIndexFinder

Note: Transformer från workspace KTH_demohuse_walls_roof_openings släppt under 3-Clause BSD License. / Framtagandet är finansierat av: / Smart Built Environments Testbädd: Smarta plan-, bygg- och förvaltningsprocesser över hela livscykeln. / Projektet Får Jag Lov koordinerat av Boverket.
Note: Connect to UUID creator for the walls (or other feature)
AttributeCreator_StoreyList_Input (input)
    -> AttributeCreator_StoreyList
Note: Connect to ListElementCounter / belonging to IfcBuildingStorey
PythonCaller_2_Input (input)
    -> PythonCaller_2
1 (output)
2 (output)
0 (output)

Bookmark: Adding index per building storey
AttributeCreator_StoreyList
    ATTR_TABLE = SET_TO storeyListIndex
    -> PythonCaller_2
PythonCaller_2
    PYTHONSYMBOL = FeatureProcessor
    NEW_ATTRIBUTES = storeyListIndex
    PYTHONSOURCE:
      import fme
      import fmeobjects
      # Template Function interface:
      # When using this function, make sure its name is set as the value of
      # the 'Class or Function to Process Features' transformer parameter
      def processFeature(feature):
          pass


      def listFinder(f): # f - the list with all features
          pos = 0 # Index in list
          while pos < len(f):
              attList = f[pos].getAllAttributeNames() # get all feature attributes
              for att in attList:
                  if 'buildingStoreysID' in att:
                      return f[pos].getAttribute('buildingStoreysID{}.ifc_unique_id')
              pos += 1
          return None

      def storeyIndexFinder(fe,storeyList):
          # Returns the index in the storey list of current feature
          parentID = fe.getAttribute('ifc_parent_unique_id')
          pos = 0
          while pos < len(storeyList):
              if storeyList[pos] == parentID:
                  return pos
              else:
                  pass # Do nothing
              pos += 1

      # Template Class Interface:
      # When using this class, make sure its name is set as the value of
      # the 'Class or Function to Process Features' transformer parameter
      class FeatureProcessor(object):
          def __init__(self):
              self.featureList = []
              self.logger = fmeobjects.FMELogFile()
              # logger.logMessageString('message')

          def input(self,feature): # This function is called every time a feature is added
              self.featureList.append(feature)

          def close(self):
              li = listFinder(self.featureList) # Return a list with storey id
              for f in self.featureList:
                  currIndex = storeyIndexFinder(f, li) # Check feature parent_id against list with storey id
                  f.setAttribute("storeyListIndex", currIndex)
                  self.pyoutput(f)
    -> Tester_StoreyIndex [off]
    -> TestFilter
TestFilter
    DEFAULT_VALUE = <UNFILTERED>
    TEST_LIST = BOOL_OP,OR,COMPOSITE_TEST,<Unused>,TEST_CLAUSE,"TEST @Value(storeyListIndex) = 1",1,BOOL_OP,OR,COMPOSITE_TEST,<Unused>,TEST_CLAUSE,"TEST @Value(storeyListIndex) = 2",2,BOOL_OP,OR,COMPOSITE_TEST,<Unused>,TEST_CLAUSE,"TEST @Value(storeyListIndex) = 0",0
    1 -> 1 (output)
    2 -> 2 (output)
    0 -> 0 (output)

Bookmark: Tester from KTH_demohouse_..
Note: Which storey index to include
Tester_StoreyIndex [off]
    TEST_MODE = Automatic
    BOOL_OP = OR
    TEST_CLAUSE = TEST @Value(storeyListIndex) = 1
    TEST_DESCRIPTION = ""

FME custom transformer Protruding_Part

Parameters:
- _ZMINVAL = @Value(_zminval)   # Zminval
- OFFSET = 500   # Buffer Amount
- DISTANCE = 3000   # Distance
- _ZMIN = @Value(_zmin)   # Zmin

Bufferer_Input (input)
    -> Bufferer
Clipper_Byggnad (input)
    -> Clipper [CLIPPEE]
Clipper
    LINES_AS_SEGMENTS = No
    BOUNDARY_CASES = Treat as Inside
    DEFAULT_VAL = 0
    MEASURE_TYPE = Continuous
    VAL_SOURCE = Clippee Only
    PRESERVE_CLIPPEE_EXTENTS = No
    CLIP_TYPE = Multiple Clippers
    CLIPPED_ATTR = _clipped
    ATTR_ACCUM_MODE = Merge Clipper
    CREATE_AGGREGATES = Yes
    ATTR_CONFLICT_RES = Use Clippee
    CONNECT_Z_MODE = First Wins
    MISSING_VAL_MODE = Compute
    INSIDE -> Output_Inside (output)
    OUTSIDE -> GeometryValidator
    <REJECTED> -> Clipper__Rejected_
Output_Inside (output)
Note: Kontrollera så att objekten har geometri
GeometryValidator
    AREA_ORIENTATION = AREA_ORIENTATION
    PRESETS = Basic Geometry Integrity
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    ISSUE_ATTR_NAME = _issues
    TYPE_REPAIR = TYPE_REPAIR
    NAN_REMOVAL = NAN_REMOVAL
    NULL_REMOVAL = NULL_REMOVAL
    CONNECT_Z_MODE_TR = First Wins
    SUMMARY = Detailed
    ARC_ENDPOINT_TOLERANCE_MODE = Auto
    ORIENTATION_CHECK_DIR = Valid
    REPAIR = Yes
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    ANGLE = 1
    CORNER_STYLE = Round
    CAP_STYLE = Round
    OFFSET = $(OFFSET)
    BUFFERED -> SurfaceFootprintReplacer
    BUFFERED -> Bufferer_Buffered
Bufferer_Buffered: Inspector [off]
SurfaceFootprintReplacer
    SHADOW_MODE = Overhead Shadow
    OFFSET_Z = @Value(_zmin)
    FOOTPRINT -> Extruder
Note: Extrude 3 el 2 m
Extruder
    DISTANCE = $(DISTANCE)
    DIRECTION = Auto
    EXTRUDED -> Clipper [CLIPPER]
    <REJECTED> -> Extruder__Rejected_
Extruder__Rejected_: Inspector

FME custom transformer CreateBasisBYA_2

Parameters:
- IFC_UNIQUE_ID = @Value(ifc_unique_id)   # Ifc Unique Id

Bookmark: BasisBYA
Input_storey (input)
    -> MinZ_2
MinZ_2
    -> SurfaceFootprintReplacer_3
SurfaceFootprintReplacer_3
    SHADOW_MODE = Overhead Shadow
    OFFSET_Z = @Value(_zminval)
    FOOTPRINT -> Dissolver_2
Input_pointCloud (input)
    -> MinZ
Input_facade (input)
    -> MinZ
MinZ
    -> SurfaceFootprintReplacer_2
SurfaceFootprintReplacer_2
    SHADOW_MODE = Overhead Shadow
    OFFSET_Z = @Value(_zminval)
    FOOTPRINT -> HullAccumulator
    <REJECTED> -> SurfaceFootprintReplacer_2__Rejected_
HullAccumulator
    DEFAULTZ = @Value(_zminval)
    HULLTYPE_PARAM = Convex ()
    3DMODE_PARAM = 3D
    GROUP_BY = ifc_unique_id _zminval
    HULL -> Dissolver_2
Dissolver_2
    DEAGGREGATE_INPUT = Yes
    NO_OVRLP = No
    CONNECT_Z_MODE = Extend
    ACCUM_INPUT_ATTRS = Merge Incoming Attributes
    AREA -> BoundsExtractor
BoundsExtractor
    ZMIN = _zmin
    ZMAX = _zmax
    XMAX = _xmax
    YMIN = _ymin
    YMAX = _ymax
    XMIN = _xmin
    -> SurfaceFootprintReplacer
SurfaceFootprintReplacer
    SHADOW_MODE = Overhead Shadow
    OFFSET_Z = @Value(_zmin)
    FOOTPRINT -> DonutHoleExtractor_2
DonutHoleExtractor_2
    DEAGGREGATE_INPUT = Yes
    OUTERSHELL -> Output (output)
Output (output)
SurfaceFootprintReplacer_2__Rejected_: Inspector [off]

Bookmark: Test1
Dissolver [off]
    DEAGGREGATE_INPUT = Yes
    NO_OVRLP = No
    CONNECT_Z_MODE = First Wins
    ACCUM_INPUT_ATTRS = Use Attributes From One Feature
    AREA -> DonutHoleExtractor [off]
    AREA -> Dissolver_Area [off]
    INTERIOR_LINE -> Dissolver_InteriorLine [off]
    <REJECTED> -> Dissolver__Rejected_ [off]
Dissolver_Area: Inspector [off]
DonutHoleExtractor [off]
    DEAGGREGATE_INPUT = Yes
    OUTERSHELL -> Aggregator [off]
Aggregator [off]
    ORDERED = No
    ACCUM_ATTRS_NAME = Use Attributes From One Feature
    AGGREGATE_TYPE = Homogeneous Collection (If Possible)
    MODE = Geometry - Assemble One Level
    SEP = ,
    AGGREGATE -> Aggregator_Aggregate [off]
Aggregator_Aggregate: Inspector [off]
Dissolver_InteriorLine: Inspector [off]
Dissolver__Rejected_: Inspector [off]

Bookmark: Test2
GeometryCoercer [off]
    GQUERY:
      for $geom in //geometry
      where $geom/count(parent::geometry) = 0
      return number($geom/@fme_id)
    KIND = fme_line
    COERCED -> Snapper_2 [off]
    UNTOUCHED -> Snapper_2 [off]
Snapper_2 [off]
    SNAPTYPE_PARAM = End Point Snapping
    TOLERANCE = 10
    EXTEND_LINES = NEVER
    SAVE_SHORT_LINES = No
    SNAPPED -> AreaBuilder [off]
    SNAPPED -> Snapper_2_Snapped [off]
    UNTOUCHED -> AreaBuilder [off]
    UNTOUCHED -> Snapper_2_Untouched [off]
AreaBuilder [off]
    LINES_AS_SEGMENTS = No
    SNAPTYPE_PARAM = None
    DROP_HOLES = No
    DONUT_CREATION = Yes
    SNAP_TOLERANCE = 0
    ALLOW_CYCLES = No
    POLY_ACCUM_ATTRS_NAME = Use Attributes From One Feature
    CONSIDER_NODE_ELEVATION = no
    POLY_LIST_ATTRS_TO_INCLUDE_MODE = Selected Attributes
    CONNECT_Z_MODE = First Wins
    CHECK_CURVE_DIRECTION = No
    AREA -> AreaAmalgamator [AREAS] [off]
    AREA -> AreaBuilder_Area [off]
AreaAmalgamator [off]
    AMALG_MODE = Binary Amalgamation
    MIN_HOLE_AREA = 100
    MAX_TRIANGLE_WIDTH = 10
    DISSOLVE_INPUT = Yes
    MAX_TRIANGLE_LENGTH = 10
    AMALGAMATED -> AreaAmalgamator_Amalgamated [off]
AreaAmalgamator_Amalgamated: Inspector [off]
AreaBuilder_Area: Inspector [off]
Snapper_2_Snapped: Inspector [off]
Snapper_2_Untouched: Inspector [off]
AreaOnAreaOverlayer [off]
    CONNECT_Z_MODE = First Wins
    OVC_ATTR = _overlaps
    ACCUM_ATTRS_NAME = Use Attributes From One Feature
    DEAGGREGATE_INPUT = Yes
    AREA -> AreaOnAreaOverlayer_Area [off]
    <REJECTED> -> AreaOnAreaOverlayer__Rejected_ [off]
AreaOnAreaOverlayer_Area: Inspector [off]
AreaOnAreaOverlayer__Rejected_: Inspector [off]

FME custom transformer MinZ_2

Input (input)
    -> AttributeCreator
AttributeCreator
    ATTR_TABLE = SET_TO _zminval
    -> BoundsExtractor
BoundsExtractor
    ZMIN = _zmin
    ZMAX = _zmax
    XMAX = _xmax
    YMIN = _ymin
    YMAX = _ymax
    XMIN = _xmin
    -> PythonCaller
PythonCaller
    PYTHONSYMBOL = FeatureProcessor
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    -> Output (output)
Output (output)

FME custom transformer StoreyIndexFinder_2

Note: Transformer från workspace KTH_demohuse_walls_roof_openings släppt under 3-Clause BSD License. / Framtagandet är finansierat av: / Smart Built Environments Testbädd: Smarta plan-, bygg- och förvaltningsprocesser över hela livscykeln. / Projektet Får Jag Lov koordinerat av Boverket.
Note: Connect to UUID creator for the walls (or other feature)
AttributeCreator_StoreyList_Input (input)
    -> AttributeCreator_StoreyList
Note: Connect to ListElementCounter / belonging to IfcBuildingStorey
PythonCaller_2_Input (input)
    -> PythonCaller_2
1 (output)
2 (output)
0 (output)

Bookmark: Adding index per building storey
AttributeCreator_StoreyList
    ATTR_TABLE = SET_TO storeyListIndex
    -> PythonCaller_2
PythonCaller_2
    PYTHONSYMBOL = FeatureProcessor
    NEW_ATTRIBUTES = storeyListIndex
    PYTHONSOURCE:
      import fme
      import fmeobjects
      # Template Function interface:
      # When using this function, make sure its name is set as the value of
      # the 'Class or Function to Process Features' transformer parameter
      def processFeature(feature):
          pass


      def listFinder(f): # f - the list with all features
          pos = 0 # Index in list
          while pos < len(f):
              attList = f[pos].getAllAttributeNames() # get all feature attributes
              for att in attList:
                  if 'buildingStoreysID' in att:
                      return f[pos].getAttribute('buildingStoreysID{}.ifc_unique_id')
              pos += 1
          return None

      def storeyIndexFinder(fe,storeyList):
          # Returns the index in the storey list of current feature
          parentID = fe.getAttribute('ifc_parent_unique_id')
          pos = 0
          while pos < len(storeyList):
              if storeyList[pos] == parentID:
                  return pos
              else:
                  pass # Do nothing
              pos += 1

      # Template Class Interface:
      # When using this class, make sure its name is set as the value of
      # the 'Class or Function to Process Features' transformer parameter
      class FeatureProcessor(object):
          def __init__(self):
              self.featureList = []
              self.logger = fmeobjects.FMELogFile()
              # logger.logMessageString('message')

          def input(self,feature): # This function is called every time a feature is added
              self.featureList.append(feature)

          def close(self):
              li = listFinder(self.featureList) # Return a list with storey id
              for f in self.featureList:
                  currIndex = storeyIndexFinder(f, li) # Check feature parent_id against list with storey id
                  f.setAttribute("storeyListIndex", currIndex)
                  self.pyoutput(f)
    -> Tester_StoreyIndex [off]
    -> TestFilter
TestFilter
    DEFAULT_VALUE = <UNFILTERED>
    TEST_LIST = BOOL_OP,OR,COMPOSITE_TEST,<Unused>,TEST_CLAUSE,"TEST @Value(storeyListIndex) = 1",1,BOOL_OP,OR,COMPOSITE_TEST,<Unused>,TEST_CLAUSE,"TEST @Value(storeyListIndex) = 2",2,BOOL_OP,OR,COMPOSITE_TEST,<Unused>,TEST_CLAUSE,"TEST @Value(storeyListIndex) = 0",0
    1 -> 1 (output)
    2 -> 2 (output)
    0 -> 0 (output)

Bookmark: Tester from KTH_demohouse_..
Note: Which storey index to include
Tester_StoreyIndex [off]
    TEST_MODE = Automatic
    BOOL_OP = OR
    TEST_CLAUSE = TEST @Value(storeyListIndex) = 1
    TEST_DESCRIPTION = ""

FME custom transformer MinZ_4

Input (input)
    -> AttributeCreator
AttributeCreator
    ATTR_TABLE = SET_TO _zminval
    -> BoundsExtractor
BoundsExtractor
    ZMIN = _zmin
    ZMAX = _zmax
    XMAX = _xmax
    YMIN = _ymin
    YMAX = _ymax
    XMIN = _xmin
    -> PythonCaller
PythonCaller
    PYTHONSYMBOL = FeatureProcessor
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    -> Output (output)
Output (output)

FME custom transformer MinZ

Input (input)
    -> AttributeCreator
AttributeCreator
    ATTR_TABLE = SET_TO _zminval
    -> BoundsExtractor
BoundsExtractor
    ZMIN = _zmin
    ZMAX = _zmax
    XMAX = _xmax
    YMIN = _ymin
    YMAX = _ymax
    XMIN = _xmin
    -> PythonCaller
PythonCaller
    PYTHONSYMBOL = FeatureProcessor
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    -> Output (output)
Output (output)

FME custom transformer PointCloudClipper

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    ATTRS_TO_PRESERVE = ifc_parent_unique_id,String
    EXTRACT_RASTER_NODATA_NAME = No
    SPACING = 20
    ACCUM_ATTRS_NAME = Yes
    GROUP_BY = ifc_unique_id
    -> Clipper_2 [CLIPPEE]
Clipper (input)
    -> Clipper_2 [CLIPPER]
Clipper_2
    LINES_AS_SEGMENTS = No
    BOUNDARY_CASES = Treat as Inside
    MEASURE_TYPE = Continuous
    VAL_SOURCE = Clippee Only
    PRESERVE_CLIPPEE_EXTENTS = No
    CLIP_TYPE = Single Clipper
    CLIPPED_ATTR = _clipped
    CREATE_AGGREGATES = Yes
    MISSING_VAL_MODE = Compute
    INSIDE -> PointCloudCoercer
    INSIDE -> Output_3D (output)
PointCloudCoercer
    CONVERT_TO_DISPLAY = Individual Points
    PART_NUMBER_ATTR_NAME = _part_number
    ACCUM_ATTRS_NAME = Yes
    POINT_COMPONENTS_PRESERVE_DISPLAY = Attributes
    COERCED -> 2DForcer
2DForcer
    2D -> HullAccumulator
HullAccumulator
    HULLTYPE_PARAM = Convex ()
    3DMODE_PARAM = 2D
    GROUP_BY = ifc_unique_id
    HULL -> Output_2D (output)
Output_2D (output)
Output_3D (output)

FME custom transformer Building_Clipper

Parameters:
- IFC_PARENT_UNIQUE_ID = @Value(ifc_parent_unique_id)   # Ifc Parent Unique Id
- DISTANCE = 10   # Distance
- OFFSET_Z = 0   # Z" Elevation

Input (input)
    -> Deaggregator
    -> BoundsExtractor
    -> BoundingBoxAccumulator
    -> Input
BoundingBoxAccumulator
    DESTINATION_SCALE = 1
    SOURCE_SCALE = 1
    ACCUM_ATTRS_NAME = Use Attributes From One Feature
    ATTR_NAME = _topferIndex
    TOPFER_INDEX = No
    BOUNDING_BOX -> FeatureMerger [REQUESTOR]
BoundsExtractor
    ZMIN = _zmin
    ZMAX = _zmax
    XMAX = _xmax
    YMIN = _ymin
    YMAX = _ymax
    XMIN = _xmin
    -> ListBuilder
ListBuilder
    LIST_ATTRS_TO_INCLUDE = _zmin ifc_parent_unique_id
    GROUPS_ORDERED = No
    LIST_NAME = _list
    -> ListRangeExtractor
ListRangeExtractor
    MAX = _max
    SRC_LIST = _list{}._zmin
    MIN = _min
    -> FeatureMerger [SUPPLIER]
FeatureMerger
    REJECT_NULL_MISSING_KEYS = No
    MERGE_TYPE = Attributes Only
    JOIN_KEYS = @Value(ifc_parent_unique_id) @Value(_list{0}.ifc_parent_unique_id) AUTO
    SUPPLIERS_FIRST = No
    ATTR_ACCUM_MODE = Merge Supplier
    IGNORE_NULLS = No
    ATTR_CONFLICT_RES = Use Requestor
    PROCESS_DUPS = No
    MERGED -> SurfaceFootprintReplacer
SurfaceFootprintReplacer
    SHADOW_MODE = Overhead Shadow
    OFFSET_Z = $(OFFSET_Z)+@Value(_min)
    FOOTPRINT -> Extruder
Extruder
    DISTANCE = $(DISTANCE)
    DIRECTION = Vertical
    EXTRUDED -> Clipper_2 [CLIPPER]
    EXTRUDED -> Output_extruded (output)
Output_extruded (output)
Deaggregator
    ID_SELECTION = ID and Parent ID
    CHILD_ID_ATTR = _hierarchy_child_id_list
    MODE = Flatten One Level
    LIST_ATTR_MODE_LOOKUP = LEAN
    ID_ATTR = _hierarchy_id
    EXPLODE_INSTANCES = No
    GEOM_NAME_FIELD = _geometry_name
    PARENT_ID_ATTR = _hierarchy_parent_id
    COPY_ATTR = Every Node
    SPLIT_COMPOSITES = No
    PART_NUMBER_FIELD = _part_number
    DEAGGREGATED -> GeometryFilter
GeometryFilter
    BREAK_AGG = No
    GEOM_PORT_NAMES = Solid
    SOLID -> Clipper_2 [CLIPPEE]
Clipper_2
    LINES_AS_SEGMENTS = No
    BOUNDARY_CASES = Treat as Inside
    MEASURE_TYPE = Continuous
    VAL_SOURCE = Clippee Only
    PRESERVE_CLIPPEE_EXTENTS = No
    CLIP_TYPE = Multiple Clippers
    CLIPPED_ATTR = _clipped
    CREATE_AGGREGATES = Yes
    MISSING_VAL_MODE = Compute
    INSIDE -> Output_clipper (output)
    <REJECTED> -> Rejected (output)
Output_clipper (output)
Rejected (output)
Input: Inspector [off]

FME custom transformer Protruding_Part_2

Parameters:
- _ZMINVAL = @Value(_zminval)   # Zminval
- OFFSET = 500   # Buffer Amount
- DISTANCE = 3000   # Distance
- _ZMIN = @Value(_zmin)   # Zmin

Bufferer_Input (input)
    -> Bufferer
Clipper_Byggnad (input)
    -> Clipper [CLIPPEE]
Clipper
    LINES_AS_SEGMENTS = No
    BOUNDARY_CASES = Treat as Inside
    DEFAULT_VAL = 0
    MEASURE_TYPE = Continuous
    VAL_SOURCE = Clippee Only
    PRESERVE_CLIPPEE_EXTENTS = No
    CLIP_TYPE = Multiple Clippers
    CLIPPED_ATTR = _clipped
    ATTR_ACCUM_MODE = Merge Clipper
    CREATE_AGGREGATES = Yes
    ATTR_CONFLICT_RES = Use Clippee
    CONNECT_Z_MODE = First Wins
    MISSING_VAL_MODE = Compute
    INSIDE -> Output_Inside (output)
    OUTSIDE -> GeometryValidator
    <REJECTED> -> Clipper__Rejected_
Output_Inside (output)
Note: Kontrollera så att objekten har geometri
GeometryValidator
    AREA_ORIENTATION = AREA_ORIENTATION
    PRESETS = Basic Geometry Integrity
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    ISSUE_ATTR_NAME = _issues
    TYPE_REPAIR = TYPE_REPAIR
    NAN_REMOVAL = NAN_REMOVAL
    NULL_REMOVAL = NULL_REMOVAL
    CONNECT_Z_MODE_TR = First Wins
    SUMMARY = Detailed
    ARC_ENDPOINT_TOLERANCE_MODE = Auto
    ORIENTATION_CHECK_DIR = Valid
    REPAIR = Yes
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    ANGLE = 1
    CORNER_STYLE = Round
    CAP_STYLE = Round
    OFFSET = $(OFFSET)
    BUFFERED -> SurfaceFootprintReplacer
    BUFFERED -> Bufferer_Buffered
Bufferer_Buffered: Inspector [off]
SurfaceFootprintReplacer
    SHADOW_MODE = Overhead Shadow
    OFFSET_Z = @Value(_zmin)
    FOOTPRINT -> Extruder
Note: Extrude 3 el 2 m
Extruder
    DISTANCE = $(DISTANCE)
    DIRECTION = Auto
    EXTRUDED -> Extruder_Extruded
    EXTRUDED -> Clipper [CLIPPER]
    <REJECTED> -> Extruder__Rejected_
Extruder_Extruded: Inspector
Extruder__Rejected_: Inspector

FME custom transformer PointCloudClipper_2

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    ATTRS_TO_PRESERVE = ifc_parent_unique_id,String
    EXTRACT_RASTER_NODATA_NAME = No
    SPACING = 20
    ACCUM_ATTRS_NAME = Yes
    GROUP_BY = ifc_unique_id
    -> Clipper_2 [CLIPPEE]
Clipper (input)
    -> Clipper_2 [CLIPPER]
Clipper_2
    LINES_AS_SEGMENTS = No
    BOUNDARY_CASES = Treat as Inside
    MEASURE_TYPE = Continuous
    VAL_SOURCE = Clippee Only
    PRESERVE_CLIPPEE_EXTENTS = No
    CLIP_TYPE = Single Clipper
    CLIPPED_ATTR = _clipped
    CREATE_AGGREGATES = Yes
    MISSING_VAL_MODE = Compute
    INSIDE -> PointCloudCoercer
    INSIDE -> Output_3D (output)
PointCloudCoercer
    CONVERT_TO_DISPLAY = Individual Points
    PART_NUMBER_ATTR_NAME = _part_number
    ACCUM_ATTRS_NAME = Yes
    POINT_COMPONENTS_PRESERVE_DISPLAY = Attributes
    COERCED -> 2DForcer
2DForcer
    2D -> HullAccumulator
HullAccumulator
    HULLTYPE_PARAM = Convex ()
    3DMODE_PARAM = 2D
    GROUP_BY = ifc_unique_id
    HULL -> Output_2D (output)
Output_2D (output)
Output_3D (output)

FME custom transformer Building_Clipper_2

Parameters:
- IFC_PARENT_UNIQUE_ID = @Value(ifc_parent_unique_id)   # Ifc Parent Unique Id
- DISTANCE = 10   # Distance
- OFFSET_Z = 0   # Z" Elevation

Input (input)
    -> Deaggregator
    -> BoundsExtractor
    -> BoundingBoxAccumulator
    -> Input
BoundingBoxAccumulator
    DESTINATION_SCALE = 1
    SOURCE_SCALE = 1
    ACCUM_ATTRS_NAME = Use Attributes From One Feature
    ATTR_NAME = _topferIndex
    TOPFER_INDEX = No
    BOUNDING_BOX -> FeatureMerger [REQUESTOR]
BoundsExtractor
    ZMIN = _zmin
    ZMAX = _zmax
    XMAX = _xmax
    YMIN = _ymin
    YMAX = _ymax
    XMIN = _xmin
    -> ListBuilder
ListBuilder
    LIST_ATTRS_TO_INCLUDE = _zmin ifc_parent_unique_id
    GROUPS_ORDERED = No
    LIST_NAME = _list
    -> ListRangeExtractor
ListRangeExtractor
    MAX = _max
    SRC_LIST = _list{}._zmin
    MIN = _min
    -> FeatureMerger [SUPPLIER]
FeatureMerger
    REJECT_NULL_MISSING_KEYS = No
    MERGE_TYPE = Attributes Only
    JOIN_KEYS = @Value(ifc_parent_unique_id) @Value(_list{0}.ifc_parent_unique_id) AUTO
    SUPPLIERS_FIRST = No
    ATTR_ACCUM_MODE = Merge Supplier
    IGNORE_NULLS = No
    ATTR_CONFLICT_RES = Use Requestor
    PROCESS_DUPS = No
    MERGED -> SurfaceFootprintReplacer
SurfaceFootprintReplacer
    SHADOW_MODE = Overhead Shadow
    OFFSET_Z = $(OFFSET_Z)+@Value(_min)
    FOOTPRINT -> Extruder
Extruder
    DISTANCE = $(DISTANCE)
    DIRECTION = Vertical
    EXTRUDED -> Clipper_2 [CLIPPER]
    EXTRUDED -> Output_extruded (output)
Output_extruded (output)
Deaggregator
    ID_SELECTION = ID and Parent ID
    CHILD_ID_ATTR = _hierarchy_child_id_list
    MODE = Flatten One Level
    LIST_ATTR_MODE_LOOKUP = LEAN
    ID_ATTR = _hierarchy_id
    EXPLODE_INSTANCES = No
    GEOM_NAME_FIELD = _geometry_name
    PARENT_ID_ATTR = _hierarchy_parent_id
    COPY_ATTR = Every Node
    SPLIT_COMPOSITES = No
    PART_NUMBER_FIELD = _part_number
    DEAGGREGATED -> GeometryFilter
GeometryFilter
    BREAK_AGG = No
    GEOM_PORT_NAMES = Solid
    SOLID -> Clipper_2 [CLIPPEE]
Clipper_2
    LINES_AS_SEGMENTS = No
    BOUNDARY_CASES = Treat as Inside
    MEASURE_TYPE = Continuous
    VAL_SOURCE = Clippee Only
    PRESERVE_CLIPPEE_EXTENTS = No
    CLIP_TYPE = Multiple Clippers
    CLIPPED_ATTR = _clipped
    CREATE_AGGREGATES = Yes
    MISSING_VAL_MODE = Compute
    INSIDE -> Output_clipper (output)
    <REJECTED> -> Rejected (output)
Output_clipper (output)
Rejected (output)
Input: Inspector [off]
