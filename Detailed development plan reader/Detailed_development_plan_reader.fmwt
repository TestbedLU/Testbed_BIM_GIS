FME workspace Detailed_development_plan_reader.fmwt
Title: Detailed_development_plan_reader

Parameters:
- SourceDataset_XML = $(FME_MF_DIR)3/Detailed development plan reader/ArildCentral.xml   # Source XML File(s)
- SourceDataset_GML = $(FME_MF_DIR)3/Detailed development plan reader/ArildCentral.xml   # Source Geography Markup Language (GML) File(s)

Readers:
- XML_1: XML from $(SourceDataset_XML)
- GML_1: GML from $(SourceDataset_GML)

Bookmark: XML Reader
plus (reader XML_1)
    attributes: plus xml_char(1), plus.href xml_char(6), xml_fragment xml_xml, xml_id xml_char(19), xml_matched_element xml_char(5), xml_parent_child_pos xml_decimal(3,0), xml_parent_id xml_char(21)
    -> detaljPlanReader [Aggregator_Input]
minus (reader XML_1)
    attributes: minus xml_char(1), minus.href xml_char(6), xml_fragment xml_xml, xml_id xml_char(20), xml_matched_element xml_char(6), xml_parent_child_pos xml_decimal(3,0), xml_parent_id xml_char(21)
    -> detaljPlanReader [Aggregator_Input]
DP_Omrade (reader XML_1)
    attributes: DP_Omrade.id xml_char(3), minus xml_char(1), minus.href xml_char(6), minus{} xml_char(1), minus{}.href xml_char(6), plus xml_char(1), plus.href xml_char(6), plus{} xml_char(1), plus{}.href xml_char(6), xml_fragment xml_xml, xml_id xml_char(21), xml_matched_element xml_char(10), xml_parent_child_pos xml_char(1), xml_parent_id xml_char(1)
    -> detaljPlanReader [FeatureMerger_Supplier]

Bookmark: GML Reader
DP_Grans (reader GML_1)
    attributes: typ{} xml_char(5), linje xml_geometry
    -> detaljPlanReader [AttributeCreator_2_Input]
DP_Omrade (reader GML_1)
    attributes: plus.nilReason xml_buffer, plus.gml_remoteSchema xml_buffer, plus.xlink_href xml_buffer, plus.xlink_title xml_buffer, plus.owns xml_boolean, minus.nilReason xml_buffer, minus.gml_remoteSchema xml_buffer, minus.xlink_href xml_buffer, minus.xlink_title xml_buffer, minus.owns xml_boolean
    -> detaljPlanReader [FeatureMerger_Requestor]
DP_Egenskapsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, bestammelsetyp xml_buffer, syfte xml_buffer, variabel{}.owns xml_boolean, variabel{}.DP_VarPunkt.namn xml_buffer, variabel{}.DP_VarPunkt.varde xml_geometry, variabel{}.DP_VarLinje.namn xml_buffer, variabel{}.DP_VarLinje.varde xml_geometry, variabel{}.DP_VarKod.namn xml_buffer, variabel{}.DP_VarKod.varde xml_buffer, variabel{}.DP_VarHeltal.namn xml_buffer, variabel{}.DP_VarHeltal.varde xml_int64, variabel{}.DP_VarText.namn xml_buffer, variabel{}.DP_VarText.varde xml_buffer, variabel{}.DP_VarDecimaltal.namn xml_buffer, variabel{}.DP_VarDecimaltal.varde xml_real64, variabel{}.DP_VarDatum.namn xml_buffer,
      variabel{}.DP_VarDatum.varde xml_date, variabel{}.DP_VarArtal.namn xml_buffer, variabel{}.DP_VarArtal.varde xml_buffer
    -> detaljPlanReader [PythonCaller_Byggnadshojd_Input]
DP_Anvandningsbestammelse (reader GML_1)
    attributes: uuid xml_buffer, bestammelseid xml_buffer, ursprunglig xml_buffer, giltighet xml_buffer, anmarkning xml_buffer, beteckning xml_buffer, index xml_buffer, insattning xml_geometry, rotation xml_buffer, omrade.nilReason xml_buffer, omrade.gml_remoteSchema xml_buffer, omrade.xlink_href xml_buffer, omrade.xlink_title xml_buffer, omrade.owns xml_boolean, anvandningsslag xml_buffer, precisering xml_buffer, huvudsaklig xml_boolean, egenskapsbestammelse{}.nilReason xml_buffer, egenskapsbestammelse{}.gml_remoteSchema xml_buffer, egenskapsbestammelse{}.xlink_href xml_buffer, egenskapsbestammelse{}.xlink_title xml_buffer, egenskapsbestammelse{}.owns xml_boolean, administrativBestammelse{}.nilReason xml_buffer, administrativBestammelse{}.gml_remoteSchema xml_buffer, administrativBestammelse{}.xlink_href xml_buffer, administrativBestammelse{}.xlink_title xml_buffer, administrativBestammelse{}.owns xml_boolean
    -> detaljPlanReader [FeatureMerger_Anvandning_Supplier]

Bookmark: Detailed development plan
  Read and modify the detailed development plan
Note: Detaljplan / Detailed development plan / Källa: Höganäs kommun, Stadsbyggnadskontoret / Source: Höganäs municipality, Urban planning office
detaljPlanReader
    ANVANDNINGSSLAG = @Value(anvandningsslag)
    OMRADE.XLINK_HREF = @Value(omrade.xlink_href)
    XML_ID = @Value(xml_id)
    UUID = @Value(uuid)
    DP_OMRADE.ID = @Value(DP_Omrade.id)
    XML_PARENT_CHILD_POS = @Value(xml_parent_child_pos)
    GML_ID = @Value(gml_id)
    XML_PARENT_ID = @Value(xml_parent_id)
    MINUS.HREF = @Value(minus.href)
    URSPRUNGLIG = @Value(ursprunglig)
    BETECKNING = @Value(beteckning)
    BESTAMMELSETYP = @Value(bestammelsetyp)
    PLUS.HREF = @Value(plus.href)
    TestFilter_2_prickMark -> FeatureColorSetter_prickadMark
    TestFilter_2_korsMark -> FeatureColorSetter_korsMark
    TestFilter_Gata -> detaljPlanReader_TestFilter_Cykel_-__detaljPlanReader_TestFilter_Cykel
    TestFilter_Gång -> detaljPlanReader_TestFilter_Cykel_-__detaljPlanReader_TestFilter_Cykel
    TestFilter_Cykel -> detaljPlanReader_TestFilter_Cykel_-__detaljPlanReader_TestFilter_Cykel
    TestFilter_Vatten -> FeatureColorSetter_Vatten
    TestFilter__Unfiltered_ -> FeatureColorSetter_OtherAreas
Junction_14
    -> Junction_15
Note: FeatureColorSetter_prickadMark : Colored
Junction_15
    -> FeatureColorSetter_prickadMark_Colored
FeatureColorSetter_prickadMark_Colored: Inspector
Junction_16
    -> Junction_17
Note: FeatureColorSetter_korsMark : Colored
Junction_17
    -> FeatureColorSetter_korsMark_Colored
FeatureColorSetter_korsMark_Colored: Inspector
detaljPlanReader_TestFilter_Cykel_-__detaljPlanReader_TestFilter_Cykel: Junction
    -> FeatureColorSetter_Gata_gang
    -> detaljPlanReader_TestFilter_Cykel_-__detaljPlanReader_TestFilter_Cykel_Output_-__Clipper_CLIPPER
detaljPlanReader_TestFilter_Cykel_-__detaljPlanReader_TestFilter_Cykel_Output_-__Clipper_CLIPPER: Junction
    -> Clipper [CLIPPER]
Junction_18
    -> Junction_19
Note: FeatureColorSetter_Gata_gang : Colored
Junction_19
    -> FeatureColorSetter_Gata_gang_Colored
FeatureColorSetter_Gata_gang_Colored: Inspector
Junction_20
    -> Junction_21
Note: FeatureColorSetter_Vatten : Colored
Junction_21
    -> FeatureColorSetter_Vatten_Colored
FeatureColorSetter_Vatten_Colored: Inspector
Junction_22
    -> Junction_23
Note: FeatureColorSetter_OtherAreas : Colored
Junction_23
    -> FeatureColorSetter_OtherAreas_Colored
FeatureColorSetter_OtherAreas_Colored: Inspector
Note: Removing the area / covering the entire / plan
Tester_EntirePlan
    TEST_DESCRIPTION = ""
    TEST_CLAUSE = TEST @Value(ID_join) != #a
    BOOL_OP = OR
    TEST_MODE = Automatic
    PASSED -> Clipper [CLIPPEE]
    PASSED -> Tester_EntirePlan_Passed
Tester_EntirePlan_Passed: Inspector

Bookmark: Set area color for visualization
FeatureColorSetter_prickadMark
    MODE = Fixed
    COLOR = 0,0,0
    FILL_COLOR = 1,0.14902,0.160784
    COLORED -> detaljPlanReader_TestFilter_Cykel_-__detaljPlanReader_TestFilter_Cykel_Output_-__Clipper_CLIPPER
    COLORED -> Junction_14
FeatureColorSetter_korsMark
    MODE = Fixed
    COLOR = 0,0,0
    FILL_COLOR = 0.423529,0.0627451,0.0666667
    COLORED -> detaljPlanReader_TestFilter_Cykel_-__detaljPlanReader_TestFilter_Cykel_Output_-__Clipper_CLIPPER
    COLORED -> Junction_16
FeatureColorSetter_Gata_gang
    MODE = Fixed
    COLOR = 0.666667,0.556863,0.552941
    FILL_COLOR = 0.666667,0.556863,0.552941
    COLORED -> Junction_18
FeatureColorSetter_Vatten
    MODE = Fixed
    COLOR = 0,0,1
    FILL_COLOR = 0,0,1
    COLORED -> Junction_20
FeatureColorSetter_OtherAreas
    MODE = Fixed
    COLOR = 0,0,0
    FILL_COLOR = 0.666667,1,0.498039
    COLORED -> Tester_EntirePlan
    COLORED -> Junction_22

Bookmark: Clipping overlapping areas for visualtisation.
  The area covering the entire plan is clipped where it overlaps other areas. Purely for visualisation.
Clipper
    MISSING_VAL_MODE = Compute
    BOUNDARY_CASES = Treat as Inside
    PRESERVE_CLIPPEE_EXTENTS = No
    ATTR_ACCUM_MODE = Merge Clipper
    CONNECT_Z_MODE = First Wins
    CLIP_TYPE = Multiple Clippers
    LINES_AS_SEGMENTS = No
    ATTR_CONFLICT_RES = Use Clippee
    CREATE_AGGREGATES = Yes
    DEFAULT_VAL = 0
    MEASURE_TYPE = Continuous
    CLIPPED_ATTR = _clipped
    VAL_SOURCE = Clippee Only
    OUTSIDE -> Clipper_Outside
Clipper_Outside: Inspector

FME custom transformer detaljPlanReader

Parameters:
- XML_PARENT_CHILD_POS = @Value(xml_parent_child_pos)   # Xml Parent Child Pos
- DP_OMRADE.ID = @Value(DP_Omrade.id)   # Dp Omrade.id
- UUID = @Value(uuid)   # uuid
- GML_ID = @Value(gml_id)   # Gml Id
- XML_PARENT_ID = @Value(xml_parent_id)   # Xml Parent Id
- ANVANDNINGSSLAG = @Value(anvandningsslag)   # anvandningsslag
- PLUS.HREF = @Value(plus.href)   # plus.href
- MINUS.HREF = @Value(minus.href)   # minus.href
- OMRADE.XLINK_HREF = @Value(omrade.xlink_href)   # Omrade.xlink Href
- BETECKNING = @Value(beteckning)   # beteckning
- BESTAMMELSETYP = @Value(bestammelsetyp)   # bestammelsetyp
- XML_ID = @Value(xml_id)   # Xml Id
- URSPRUNGLIG = @Value(ursprunglig)   # ursprunglig

Aggregator_Input (input)
    -> Aggregator
Note: Create list with gränser per område
Aggregator
    GROUP_BY = xml_parent_id
    MODE = Attributes Only
    ACCUM_ATTRS_NAME = Merge Incoming Attributes
    SEP = ,
    ORDERED = No
    LIST_NAME = childList
    LIST_ATTRS_TO_INCLUDE = minus.href plus.href xml_parent_child_pos
    AGGREGATE -> PolygonCreator
AttributeCreator_2_Input (input)
    -> AttributeCreator_2
Note: Create ID for later join
AttributeCreator_2
    ATTR_TABLE = SET_TO ID_join = #@Value(gml_id)
    -> PolygonCreator
Note: Creates polygons over Områden.
PolygonCreator: PythonCaller
    PYTHONSYMBOL = FeatureProcessor
    PYTHONSOURCE:
      import fme
      import fmeobjects

      # Finds and returns the requested gräns
      def gransFinder(id,gransList):
          for grans in gransList:
              if grans.getAttribute('ID_join') == id:
                  return grans

      # Finds first line segment in a boundary, either outer or inner polygon
      def initialBoundaryLine(polygonBoundaryParts):
          geo = polygonBoundaryParts.getGeometry()

          nbrLines = geo.numParts()

          # Taking first part of the FMEPath
          polygonBoundary = geo.getPartAt(0)

          if type(polygonBoundary) == fmeobjects.FMEArc:
              polygonBoundary = polygonBoundary.getAsLine()

          # Iterating over the parts in the FMEPath object
          for tp in xrange(1,nbrLines):
              tpl = geo.getPartAt(tp) # Next part (at index tp)

              # Needs to be an FMELine
              if type(tpl) == fmeobjects.FMEArc:
                  tpl = tpl.getAsLine()

              polygonBoundary.appendLine(tpl)

          return polygonBoundary

      # #################################################################
      # FeatureProcessor
      # #################################################################
      class FeatureProcessor(object):
          def __init__(self):
              self.omrade = []
              self.grans = []

          # Saving in different lists depending on if the feature is a gräns or område
          def input(self,feature):
              if feature.hasGeometry():
                  self.grans.append(feature)
              else:
                  self.omrade.append(feature)

          def close(self):

              # Iterating over all Områden sent to the PythonCaller
              for omr in self.omrade:
                  boundaryList = []
                  tempGrans = True # Will stop the loop after last item is found (temp = None)
                  index = 0 # Index of "Gräns"
                  innerIndex = 0 # For keeping track of holes
                  firstLine = True # If first line segment of a gräns

                  #Looping over all "gränser" in current "Område"
                  while tempGrans != None:
                      tempGrans = omr.getAttribute('childList{%i}.xml_parent_child_pos' % (index))

                      # Already found last "gräns" of the "område"
                      if not tempGrans:
                          break
                      tempGrans = int(tempGrans)

                      if not tempGrans == index: # To break in case something is wrong wth indices
                          print 'Index not correct'
                          break

                      # Retreiving the next segment and finding direction.
                      minusTest = omr.getAttribute('childList{%i}.minus.href' % (index))
                      if minusTest != None:
                          minus = True
                          tempGransID = minusTest
                      else:
                          minus = False
                          tempGransID = omr.getAttribute('childList{%i}.plus.href' % (index))

                      # Building line
                      # This part is for the first "Gräns" either in the outer (index == 0) polygon or
                      # a hole (innerIndex >= 1)
                      if firstLine:
                          partOne = gransFinder(tempGransID, self.grans)
                          polygonBoundary = initialBoundaryLine(partOne)
                          firstLine = False
                          if minus:
                              polygonBoundary.reverse()


                      # From the second "gräns" in the list.
                      else:
                          polygonBoundaryParts = gransFinder(tempGransID, self.grans)

                          geo = polygonBoundaryParts.getGeometry()

                          nbrLines = geo.numParts()

                          tmpLine = geo.getPartAt(0)

                          if type(tmpLine) == fmeobjects.FMEArc:
                              tmpLine = tmpLine.getAsLine()

                          #Iterating over the of the parts in the FMEPath object
                          for tp in xrange(1,nbrLines):

                              tpl = geo.getPartAt(tp)

                              if type(tpl) == fmeobjects.FMEArc:
                                  tpl = tpl.getAsLine()

                              tmpLine.appendLine(tpl)

                          if minus:
                              tmpLine.reverse()

                          polygonBoundary.appendLine(tmpLine)

                      # True if a closed polygon is found.
                      if polygonBoundary.isClosed(False): # False => not considering 3D
                          firstLine = True # Next will be first line of an inner polygon (if existing)
                          innerIndex += 1 # Counting inner polygons
                          boundaryList.append(polygonBoundary) # Appending current polygon to list
                          polygonBoundary = None

                      index += 1

                  # Final part: Creating the polygons incl. holes if present
                  # Creating a polygon with the outer boundary by popping it from the list of ploygons
                  if boundaryList:
                      outerPoly = fmeobjects.FMEDonut(boundaryList.pop(0))
                      # Iterating over all inner polygons that were found (the ouoter is already removed above)
                      for omrPoly in boundaryList:
                          innerPoly = fmeobjects.FMEDonut(omrPoly)
                          outerPoly.addInnerBoundaryCurve(omrPoly)

                      omr.setGeometry(outerPoly)

                      self.pyoutput(omr)
    -> FeatureMerger_2 [REQUESTOR]
PythonCaller_Byggnadshojd_Input (input)
    -> PythonCaller_Byggnadshojd
Note: Finds byggnadshöjd / (Other heights not considered)
PythonCaller_Byggnadshojd
    PYTHONSYMBOL = processFeature
    PYTHONSOURCE:
      import fme
      import fmeobjects

      # Template Function interface:
      # When using this function, make sure its name is set as the value of
      # the 'Class or Function to Process Features' transformer parameter
      def processFeature(feature):

          if feature.getAttribute('bestammelsetyp')  == 'DP_KM_Eg_Omfatt_Byggnadshojd':
              byHojd = feature.getAttribute('beteckning')
              byHojd = byHojd.replace(',', '.')
              byHojd = float(byHojd)
              feature.setAttribute('byggnadshojd', byHojd)
    NEW_ATTRIBUTES = byggnadshojd
    -> FeatureMerger_Egenskap [SUPPLIER]
    -> GeometryFilter
GeometryFilter
    BREAK_AGG = No
    GEOM_PORT_NAMES = Point
    POINT -> PointOnAreaOverlayer [POINT]
    <UNFILTERED> -> GeometryFilter_2
Note: Unfiltered, regulations with link, no geometry.
GeometryFilter_2
    BREAK_AGG = No
    GEOM_PORT_NAMES = Line Arc Null
    NULL -> FeatureMerger_4 [SUPPLIER]
FeatureMerger_Anvandning_Supplier (input)
    -> FeatureMerger_Anvandning [SUPPLIER]
FeatureMerger_Requestor (input)
    -> FeatureMerger [REQUESTOR]
FeatureMerger_Supplier (input)
    -> FeatureMerger [SUPPLIER]
Note: Needs xml_id from the / XML-reader to join with lines.
FeatureMerger
    MERGE_TYPE = Attributes Only
    REJECT_NULL_MISSING_KEYS = No
    ATTR_ACCUM_MODE = Merge Supplier
    IGNORE_NULLS = No
    ATTR_CONFLICT_RES = Use Requestor
    JOIN_KEYS = @Value(gml_id) @Value(DP_Omrade.id) AUTO
    SUPPLIERS_FIRST = No
    PROCESS_DUPS = No
    MERGED -> AttributeKeeper
AttributeKeeper
    KEEP_ATTRS = xml_id,gml_id,xml_fragment,DP_Omrade.id,gml_parent_id
    -> AttributeCreator
AttributeCreator
    ATTR_TABLE = SET_TO ID_join = #@Value(DP_Omrade.id)
    -> FeatureMerger_Egenskap [REQUESTOR]
AttributeRemover
    REMOVE_ATTRS = minus,plus
    -> FeatureMerger_2 [SUPPLIER]
Note: Adding Geometries to bestämmelser
FeatureMerger_2
    MERGE_TYPE = Attributes and Geometry
    REJECT_NULL_MISSING_KEYS = No
    ATTR_ACCUM_MODE = Merge Supplier
    IGNORE_NULLS = No
    ATTR_CONFLICT_RES = Use Requestor
    JOIN_KEYS = @Value(xml_parent_id) @Value(xml_id) AUTO
    SUPPLIERS_FIRST = No
    PROCESS_DUPS = No
    MERGED -> AttributeRemover_2
    MERGED -> FeatureMerger_3 [REQUESTOR]
AttributeRemover_2
    LIST_ATTRS = childList{}
    REMOVE_ATTRS = xml_id,gml_id,xml_parent_child_pos,ID_join,plus.href,xml_matched_element,plus,minus.href,linje
    -> PointOnAreaOverlayer [AREA]
Note: NB!!!!!!!!!!!!!!!!!!!!!!!! / Swap ports Merged and / UnmergedRequestor if using / areas allowed to build
Note: Merging attributes from / areas allowed to build.
FeatureMerger_3
    MERGE_TYPE = Attributes Only
    REJECT_NULL_MISSING_KEYS = No
    ATTR_ACCUM_MODE = Merge Supplier
    IGNORE_NULLS = No
    ATTR_CONFLICT_RES = Use Requestor
    JOIN_KEYS = @Value(DP_Omrade.id) @Value(DP_Omrade.id) AUTO
    SUPPLIERS_FIRST = No
    PROCESS_DUPS = No
    MERGED -> FeatureMerger_4 [REQUESTOR]
Note: Merging with bestämmelser without geometry. / Areas not allowed to build (prickad mark) and / only "komplementbyggnad (korsmark)
FeatureMerger_4
    MERGE_TYPE = Attributes and Geometry
    REJECT_NULL_MISSING_KEYS = No
    ATTR_ACCUM_MODE = Merge Supplier
    IGNORE_NULLS = No
    CONNECT_Z_MODE = First Wins
    ATTR_CONFLICT_RES = Use Requestor
    JOIN_KEYS = @Value(omrade.xlink_href) @Value(omrade.xlink_href) AUTO
    SUPPLIERS_FIRST = No
    PROCESS_DUPS = Yes
    GEOM_TYPE = Build Polygons
    MERGED -> TestFilter_2
    UNMERGED_REQUESTOR -> TestFilter
    <REJECTED> -> FeatureMerger_4__Rejected_
Note: Splitting prickar mark and korsmark
TestFilter_2
    DEFAULT_VALUE = <UNFILTERED>
    TEST_LIST = BOOL_OP,OR,COMPOSITE_TEST,<Unused>,TEST_CLAUSE,"TEST @Value(bestammelsetyp) CONTAINS Prick",prickMark,BOOL_OP,OR,COMPOSITE_TEST,<Unused>,TEST_CLAUSE,"TEST @Value(bestammelsetyp) CONTAINS Kors",korsMark
    prickMark -> TestFilter_2_prickMark (output)
    korsMark -> TestFilter_2_korsMark (output)
TestFilter_2_prickMark (output)
TestFilter_2_korsMark (output)
TestFilter
    DEFAULT_VALUE = <UNFILTERED>
    TEST_LIST = BOOL_OP,OR,COMPOSITE_TEST,<Unused>,TEST_CLAUSE,"TEST @Value(anvandningsslag) CONTAINS gata",Gata,BOOL_OP,OR,COMPOSITE_TEST,<Unused>,TEST_CLAUSE,"TEST @Value(anvandningsslag) CONTAINS gang",Gång,BOOL_OP,OR,COMPOSITE_TEST,<Unused>,TEST_CLAUSE,"TEST @Value(anvandningsslag) CONTAINS cykel",Cykel,BOOL_OP,OR,COMPOSITE_TEST,<Unused>,TEST_CLAUSE,"TEST @Value(beteckning) CONTAINS vatten",Vatten
    Gata -> TestFilter_Gata (output)
    Gång -> TestFilter_Gång (output)
    Cykel -> TestFilter_Cykel (output)
    Vatten -> TestFilter_Vatten (output)
    <UNFILTERED> -> TestFilter__Unfiltered_ (output)
TestFilter_Gata (output)
TestFilter_Gång (output)
TestFilter_Cykel (output)
TestFilter_Vatten (output)
TestFilter__Unfiltered_ (output)
FeatureMerger_4__Rejected_: Inspector

Bookmark: Connects bestämmelser to områden
FeatureMerger_Egenskap
    MERGE_TYPE = Attributes Only
    REJECT_NULL_MISSING_KEYS = No
    ATTR_ACCUM_MODE = Merge Supplier
    IGNORE_NULLS = No
    CONNECT_Z_MODE = First Wins
    ATTR_CONFLICT_RES = Use Requestor
    JOIN_KEYS = @Value(ID_join) @Value(omrade.xlink_href) AUTO
    LIST_NAME = EgenskapList
    SUPPLIERS_FIRST = No
    LIST_ATTRS_TO_INCLUDE = beteckning ursprunglig uuid
    PROCESS_DUPS = Yes
    GEOM_TYPE = Build Polygons
    MERGED -> FeatureMerger_Anvandning [REQUESTOR]
    UNMERGED_REQUESTOR -> FeatureMerger_Anvandning [REQUESTOR]
FeatureMerger_Anvandning
    MERGE_TYPE = Attributes Only
    REJECT_NULL_MISSING_KEYS = No
    ATTR_ACCUM_MODE = Merge Supplier
    IGNORE_NULLS = No
    CONNECT_Z_MODE = First Wins
    ATTR_CONFLICT_RES = Use Requestor
    JOIN_KEYS = @Value(ID_join) @Value(omrade.xlink_href) AUTO
    LIST_NAME = AnvandningList_beteckning
    SUPPLIERS_FIRST = No
    LIST_ATTRS_TO_INCLUDE = beteckning ursprunglig uuid
    PROCESS_DUPS = Yes
    GEOM_TYPE = Build Polygons
    MERGED -> AttributeRemover
    UNMERGED_REQUESTOR -> AttributeRemover

Bookmark: Finds area where buildings are permitted
Note: To get egenskaper from points
PointOnAreaOverlayer
    ATTR_ACCUM_MODE = Merge Incoming
    CANDIDATE_LIST_ATTRS_TO_INCLUDE = beteckning ursprunglig variabel{}.DP_VarArtal.namn variabel{}.DP_VarArtal.varde variabel{}.DP_VarDatum.namn variabel{}.DP_VarDatum.varde variabel{}.DP_VarDecimaltal.namn variabel{}.DP_VarDecimaltal.varde variabel{}.DP_VarHeltal.namn variabel{}.DP_VarHeltal.varde variabel{}.DP_VarKod.namn variabel{}.DP_VarKod.varde variabel{}.DP_VarLinje.namn variabel{}.DP_VarLinje.varde variabel{}.DP_VarPunkt.namn variabel{}.DP_VarPunkt.varde variabel{}.DP_VarText.namn variabel{}.DP_VarText.varde variabel{}.owns
    ATTR_CONFLICT_RES = Use Original
    DEAGGREGATE_INPUT = Yes
    CANDIDATE_LIST_ATTRS_TO_INCLUDE_MODE = Selected Attributes
    CANDIDATE_LIST_NAME = egenskap
    OV_ATTR = _overlaps
    POLYS_FIRST = NO
    AREA -> PythonCaller_Nockhojd
Note: Finds max nockhöjd / (Other heights not considered)
PythonCaller_Nockhojd
    PYTHONSYMBOL = processFeature
    PYTHONSOURCE:
      import fme
      import fmeobjects
      # Template Function interface:
      # When using this function, make sure its name is set as the value of
      # the 'Class or Function to Process Features' transformer parameter
      def processFeature(feature):
          testString = 'gsta nockh'
          i = 0
          item = feature.getAttribute('egenskap{%i}.ursprunglig' % (i))
          maxNock = None

          while item:
              if testString in item:
                  maxNock = feature.getAttribute('egenskap{%i}.beteckning' % (i))
                  break
              i += 1
              item = feature.getAttribute('egenskap{%i}.ursprunglig' % (i))
          if maxNock:
              maxNock = maxNock.replace(",",".")
              maxNock = float(maxNock)
              feature.setAttribute('max_nock', maxNock)
    NEW_ATTRIBUTES = max_nock
    -> PythonCaller_Takvinkel
Note: Finds min and max takvinkel
PythonCaller_Takvinkel
    PYTHONSYMBOL = processFeature
    PYTHONSOURCE:
      import fme
      import fmeobjects
      # Template Function interface:
      # When using this function, make sure its name is set as the value of
      # the 'Class or Function to Process Features' transformer parameter
      def processFeature(feature):
          testString_1 = 'gsta taklutning'
          teststring_2 = 'taklutning i grader'
          i = 0
          item = feature.getAttribute('egenskap{%i}.ursprunglig' % (i))
          maxTakVinkel = False
          minTakVinkel = False

          while item:
              if testString_1 in item:
                  maxTakVinkel = feature.getAttribute('egenskap{%i}.beteckning' % (i))
                  break
              elif teststring_2 in item:
                  varIndex = 0
                  varItem = feature.getAttribute('egenskap{%i}.variabel{%i}.DP_VarDecimaltal.namn' % (i, varIndex))
                  while varItem:
                      if 'minvinkel' in varItem:
                          minTakVinkel = feature.getAttribute('egenskap{%i}.variabel{%i}.DP_VarDecimaltal.varde' % (i, varIndex))
                      elif 'maxvinkel' in varItem:
                          maxTakVinkel = feature.getAttribute('egenskap{%i}.variabel{%i}.DP_VarDecimaltal.varde' % (i, varIndex))
                      varIndex += 1
                      varItem = feature.getAttribute('egenskap{%i}.variabel{%i}.DP_VarDecimaltal.namn' % (i, varIndex))
              i += 1
              item = feature.getAttribute('egenskap{%i}.ursprunglig' % (i))

          if maxTakVinkel:
              #maxTakVinkel = maxTakVinkel.replace(",",".")
              #maxTakVinkel = float(maxTakVinkel)
              feature.setAttribute('max_takvinkel', maxTakVinkel)
          if minTakVinkel:
              feature.setAttribute('min_takvinkel', minTakVinkel)
    NEW_ATTRIBUTES = max_takvinkel min_takvinkel
    -> AttributeKeeper_2
AttributeKeeper_2
    KEEP_ATTRS = max_nock,DP_Omrade.id,max_takvinkel,byggnadshojd,min_takvinkel
    -> FeatureMerger_3 [SUPPLIER]
