FME workspace Multihuset - utan objekt för BYA.fmw
Title: Multihuset - utan objekt för BYA

Parameters:
- SourceDataset_IFC =   # Source Industry Foundation Class (IFC) File(s)

Readers:
- IFC_1: IFC from $(SourceDataset_IFC)

IfcSlab (reader IFC_1)
    attributes: GlobalId char(22), Name string, Description string, ObjectType string, Tag string, PredefinedType enumeration, Axis geometry, Body geometry, Box geometry, FootPrint geometry
    -> TestFilter
    -> TestFilter_3
Note: Tar bort slabs som är väg, trottoar och gräsmatta.
TestFilter_3
    TEST_LIST:
      BOOL_OP,AND,COMPOSITE_TEST,<Unused>,TEST_CLAUSE,"TEST @Value(ifc_parent_id) != 2wAwLTUELBoug$uZM3p2lo
      TEST @Value(ifc_parent_id) != 2wAwLTUELBoug$uZM3p2jY
      TEST @Value(ifc_parent_id) != 2wAwLTUELBoug$uZM3p2Wq
      TEST @Value(ifc_unique_id) != 1KzVLxChPEchQfE4o0XBGj_128
      TEST @Value(ifc_unique_id) != 3ZNACLJKP6Efb2$KMfjv7r_119084
      TEST @Value(ifc_unique_id) != 0wB2kynn11nBpZLmutB1dx_119087",Sorted
    DEFAULT_VALUE = <UNFILTERED>
    Sorted -> ListBasedFeatureMerger [SUPPLIER]
    Sorted -> Clipper_5m_Custom
    Sorted -> Clipper_3m_Custom
Note: Väljer ut botten slabs
Note: Klipper byggnaden för att kunna ta ut utkragande delar.
TestFilter
    TEST_LIST:
      BOOL_OP,OR,COMPOSITE_TEST,<Unused>,TEST_CLAUSE,"TEST @Value(ifc_unique_id) = 004S$qRavFBgFZvx6kXFaM_52761
      TEST @Value(ifc_unique_id) = 2ZsYnNhLn9pxPHDlMkMRHI_106184",Bottom slab
    DEFAULT_VALUE = <UNFILTERED>
    Bottom slab -> CreateBasisBYA [Input_storey]
Note: Sorterar bort objekt som är murar utanför byggnaden
TestFilter_2
    TEST_LIST:
      BOOL_OP,AND,COMPOSITE_TEST,<Unused>,TEST_CLAUSE,"TEST @Value(ifc_unique_id) != 0ZXwU$BHf25Rfw0jifbRUv_117777
      TEST @Value(ifc_unique_id) != 2imSLrgPvCS9HZU5E_bfV3_141663
      TEST @Value(ifc_unique_id) != 2imSLrgPvCS9HZU5E_bfV0_141613
      TEST @Value(ifc_unique_id) != 26NIHmMWH4dwkkEu8dM1VW_117001
      TEST @Value(ifc_unique_id) != 26NIHmMWH4dwkkEu8dM1OS_117057
      TEST @Value(ifc_unique_id) != 26NIHmMWH4dwkkEu8dM1Rz_117207
      TEST @Value(ifc_unique_id) != 26NIHmMWH4dwkkEu8dM1Pj_117107
      TEST @Value(ifc_unique_id) != 26NIHmMWH4dwkkEu8dM1Ql_117157
      TEST @Value(ifc_unique_id) != 26NIHmMWH4dwkkEu8dM1H9_117407
      TEST @Value(ifc_unique_id) != 26NIHmMWH4dwkkEu8dM1Ij_117457
      TEST @Value(ifc_unique_id) != 26NIHmMWH4dwkkEu8dM1NU_117307
      TEST @Value(ifc_unique_id) != 26NIHmMWH4dwkkEu8dM1GM_117357
      TEST @Value(ifc_unique_id) != 26NIHmMWH4dwkkEu8dM1LP_117257",Passed walls
    DEFAULT_VALUE = <UNFILTERED>
    Passed walls -> FacadeBottomEdgeClipper_Custom
    Passed walls -> ListBasedFeatureMerger [SUPPLIER]
    Passed walls -> Clipper_3m_Custom
    Passed walls -> Clipper_5m_Custom
FacadeBottomEdgeClipper_Custom: Building_Clipper_Custom
    DISTANCE = 10
    OFFSET_Z = 0
    IFC_PARENT_UNIQUE_ID = @Value(ifc_parent_unique_id)
    Output_extruded -> PointCloudClipper_2 [Clipper]
    Output_clipper -> CreateBasisBYA [Input_facade]
    Rejected -> PointCloudClipper_2 [Wall]
PointCloudClipper_2
    IFC_UNIQUE_ID = @Value(ifc_unique_id)
    IFC_PARENT_UNIQUE_ID = @Value(ifc_parent_unique_id)
    Output_2D -> CreateBasisBYA [Input_pointCloud]
IfcDoor (reader IFC_1)
    attributes: GlobalId char(22), Name string, Description string, ObjectType string, Tag string, OverallHeight real, OverallWidth real, Axis geometry, Body geometry, Box geometry, FootPrint geometry
    -> FacadeBottomEdgeClipper_Custom_2
    -> Clipper_5m_Custom
    -> Clipper_3m_Custom
    -> ListBasedFeatureMerger [SUPPLIER]
Note: Glaspartier
IfcMember (reader IFC_1)
    attributes: GlobalId char(22), Name string, Description string, ObjectType string, Tag string, Axis geometry, Body geometry, Box geometry, FootPrint geometry
    -> FacadeBottomEdgeClipper_Custom_2
    -> Clipper_5m_Custom
    -> Clipper_3m_Custom
    -> ListBasedFeatureMerger [SUPPLIER]
FacadeBottomEdgeClipper_Custom_2: Building_Clipper_Custom
    DISTANCE = 10
    OFFSET_Z = 0
    IFC_PARENT_UNIQUE_ID = @Value(ifc_parent_unique_id)
    Output_clipper -> CreateBasisBYA [Input_facade]
CreateBasisBYA
    IFC_UNIQUE_ID = @Value(ifc_unique_id)
    -> CreateBasisBYA_HJVH_Output
    -> SurfaceFootprintReplacer_3
    -> AttributeManager_2
    -> Protruding_Part [Bufferer_Input]
CreateBasisBYA_HJVH_Output: Inspector

Bookmark: Väggar
IfcWallStandardCase (reader IFC_1)
    attributes: GlobalId char(22), Name string, Description string, ObjectType string, Tag string, Axis geometry, Body geometry, Box geometry, FootPrint geometry
    -> TestFilter_2
IfcWall (reader IFC_1)
    attributes: GlobalId char(22), Name string, Description string, ObjectType string, Tag string, Axis geometry, Body geometry, Box geometry, FootPrint geometry
    -> TestFilter_2

Bookmark: Klipper byggnaden 0-3 m
Clipper_3m_Custom: Building_Clipper_Custom
    DISTANCE = 3000
    OFFSET_Z = 0
    IFC_PARENT_UNIQUE_ID = @Value(ifc_parent_unique_id)
    Output_extruded -> PointCloudClipper_5 [Clipper]
    Output_clipper -> Protruding_Part [Clipper_Byggnad]
    Rejected -> PointCloudClipper_5 [Wall]
PointCloudClipper_5
    IFC_UNIQUE_ID = @Value(ifc_unique_id)
    IFC_PARENT_UNIQUE_ID = @Value(ifc_parent_unique_id)
    Output_3D -> Protruding_Part [Clipper_Byggnad]

Bookmark: Klipper byggnaden 3-5 m
Clipper_5m_Custom: Building_Clipper_Custom
    DISTANCE = 2000
    OFFSET_Z = 3000
    IFC_PARENT_UNIQUE_ID = @Value(ifc_parent_unique_id)
    Output_extruded -> PointCloudClipper_6 [Clipper]
    Output_clipper -> AttributeManager
    Rejected -> PointCloudClipper_6 [Wall]
PointCloudClipper_6
    IFC_UNIQUE_ID = @Value(ifc_unique_id)
    IFC_PARENT_UNIQUE_ID = @Value(ifc_parent_unique_id)
    Output_3D -> AttributeManager

Bookmark: 3-5m, < 1,5m
AttributeManager
    ATTR_TABLE = SET_TO minz_value = @Value(minz_value)+3000
    -> Protruding_Part_2 [Clipper_Byggnad]
Note: Flytta zmin +3000mm
AttributeManager_2
    ATTR_TABLE:
      SET_TO _zminval = @Value(_zminval)+3000
      SET_TO _zmin = @Value(_zmin)+3000
    -> Protruding_Part_2 [Bufferer_Input]
Protruding_Part_2
    DISTANCE = 2000
    OFFSET = 1500
    _ZMINVAL = 6400
    Output_Outside -> Utkragande_del_2_Output_Outside_2
    Output_Outside -> Aggregator
Utkragande_del_2_Output_Outside_2: Inspector

Bookmark: 0-3m, < 0,5m
Protruding_Part
    DISTANCE = 3000
    OFFSET = 500
    _ZMINVAL = 3400
    Output_Outside -> Utkragande_del_Output_Outside_2
    Output_Outside -> Aggregator
Utkragande_del_Output_Outside_2: Inspector

Bookmark: Utkragade delar
Note: Klipper de utkragande delarna (Output_Outside)
Aggregator
    MODE = Attributes Only
    LIST_NAME = ListName
    ORDERED = No
    CONCAT_ATTRS = ifc_unique_id
    LIST_ATTRS_TO_INCLUDE = ifc_unique_id
    SEP = ,
    ACCUM_ATTRS_NAME = Merge Incoming Attributes
    AGGREGATE -> ListElementCounter
ListElementCounter
    CNT_ATTR = nbrStoreys
    LIST_NAME = ListName{}
    -> ListBasedFeatureMerger [REQUESTOR]
Note: Hämtar hela utkragande objekt mha ifc_unique_id, projicerar och lägger samman men "BasisBYA"
ListBasedFeatureMerger
    BUILD_INCOMPLETE = Merge Supplier Information
    REFERATTR = ListName{}.ifc_unique_id
    PROCESS_DUPS = Yes
    MERGE_TYPE = Geometry
    MODE = AUTO
    REFEEATTR = @Value(ifc_unique_id)
    GEOM_TYPE = Build Aggregates
    MERGED -> SurfaceFootprintReplacer_2
SurfaceFootprintReplacer_2
    SHADOW_MODE = Overhead Shadow
    OFFSET_Z = 0
    FOOTPRINT -> GeometryCoercer
SurfaceFootprintReplacer_3
    SHADOW_MODE = Overhead Shadow
    OFFSET_Z = 0
    FOOTPRINT -> GeometryCoercer
Dissolver_2
    NO_OVRLP = No
    ACCUM_INPUT_ATTRS = Use Attributes From One Feature
    DEAGGREGATE_INPUT = Yes
    CONNECT_Z_MODE = First Wins
    AREA -> DonutHoleExtractor
DonutHoleExtractor
    DEAGGREGATE_INPUT = Yes
    OUTERSHELL -> AreaCalculator_2

Bookmark: Custom
  Tar bort hål och sammanfogar delar.
GeometryCoercer
    GQUERY:
      for $geom in //geometry
      where $geom/count(parent::geometry) = 0
      return number($geom/@fme_id)
    KIND = fme_line
    COERCED -> Snapper
    UNTOUCHED -> Snapper
Snapper
    CLEANING_TOLERANCE_MODE = AUTO
    SNAPTYPE_PARAM = Segment Snapping
    TOLERANCE = 10
    SNAPPED -> AreaBuilder
    UNTOUCHED -> AreaBuilder
AreaBuilder
    LINES_AS_SEGMENTS = No
    SNAPTYPE_PARAM = None
    SNAP_TOLERANCE = 0
    POLY_ACCUM_ATTRS_NAME = Use Attributes From One Feature
    CHECK_CURVE_DIRECTION = No
    DROP_HOLES = No
    CONSIDER_NODE_ELEVATION = no
    DONUT_CREATION = Yes
    CONNECT_Z_MODE = First Wins
    POLY_LIST_ATTRS_TO_INCLUDE_MODE = Selected Attributes
    ALLOW_CYCLES = No
    AREA -> Dissolver_2

Bookmark: Areaberäkning
Note: Beräkna BYA
AreaCalculator_2
    AREA_TYPE = Plane Area
    AREA_ATTR = _area
    MULT = 1/1000000
    -> AttributeRounder
Note: Avrunda till en decimal
AttributeRounder
    SRC_ATTRS = _area
    ROUND_TYPE = Nearest
    PLACES = 1
    -> AttributeKeeper
AttributeKeeper
    KEEP_ATTRS = _area
    -> AttributeKeeper_Output
AttributeKeeper_Output: Inspector

FME custom transformer Building_Clipper_Custom

Parameters:
- IFC_PARENT_UNIQUE_ID = @Value(ifc_parent_unique_id)   # Ifc Parent Unique Id
- DISTANCE = 10   # Distance
- OFFSET_Z =   # Z" Elevation

Input (input)
    -> BoundingBoxAccumulator
    -> Deaggregator
BoundingBoxAccumulator
    ATTR_NAME = _topferIndex
    ACCUM_ATTRS_NAME = Use Attributes From One Feature
    SOURCE_SCALE = 1
    TOPFER_INDEX = No
    DESTINATION_SCALE = 1
    BOUNDING_BOX -> AttributeCreator
SurfaceFootprintReplacer
    SHADOW_MODE = Overhead Shadow
    OFFSET_Z = $(OFFSET_Z)+@Value(minz_value)
    FOOTPRINT -> Extruder
Extruder
    DISTANCE = $(DISTANCE)
    DIRECTION = Vertical
    EXTRUDED -> Clipper_2 [CLIPPER]
    EXTRUDED -> Output_extruded (output)
    EXTRUDED -> Extruder_Extruded
Extruder_Extruded: Inspector
Output_extruded (output)
Deaggregator
    GEOM_NAME_FIELD = _geometry_name
    COPY_ATTR = Every Node
    LIST_ATTR_MODE_LOOKUP = LEAN
    MODE = Flatten One Level
    ID_SELECTION = ID and Parent ID
    ID_ATTR = _hierarchy_id
    PARENT_ID_ATTR = _hierarchy_parent_id
    CHILD_ID_ATTR = _hierarchy_child_id_list
    PART_NUMBER_FIELD = _part_number
    EXPLODE_INSTANCES = No
    SPLIT_COMPOSITES = No
    DEAGGREGATED -> GeometryFilter
GeometryFilter
    BREAK_AGG = No
    GEOM_PORT_NAMES = Solid
    SOLID -> Clipper_2 [CLIPPEE]
Clipper_2
    LINES_AS_SEGMENTS = No
    MEASURE_TYPE = Continuous
    CREATE_AGGREGATES = Yes
    BOUNDARY_CASES = Treat as Inside
    MISSING_VAL_MODE = Compute
    CLIPPED_ATTR = _clipped
    CLIP_TYPE = Multiple Clippers
    VAL_SOURCE = Clippee Only
    PRESERVE_CLIPPEE_EXTENTS = No
    INSIDE -> Output_clipper (output)
    <REJECTED> -> Rejected (output)
Output_clipper (output)
Rejected (output)

Bookmark: Custom
  Sätter minz till 3400 mm
AttributeCreator
    ATTR_TABLE = SET_TO minz_value = 3400
    -> SurfaceFootprintReplacer

FME custom transformer Protruding_Part

Parameters:
- _ZMINVAL = 0   # Zminval
- OFFSET = 500   # Buffer Amount
- DISTANCE = 3000   # Distance

Bufferer_Input (input)
    -> Bufferer
Clipper_Byggnad (input)
    -> Clipper [CLIPPEE]
Clipper
    LINES_AS_SEGMENTS = No
    MEASURE_TYPE = Continuous
    CREATE_AGGREGATES = Yes
    DEFAULT_VAL = 0
    BOUNDARY_CASES = Treat as Inside
    MISSING_VAL_MODE = Compute
    ATTR_CONFLICT_RES = Use Clippee
    CLIPPED_ATTR = _clipped
    CLIP_TYPE = Multiple Clippers
    VAL_SOURCE = Clippee Only
    PRESERVE_CLIPPEE_EXTENTS = No
    CONNECT_Z_MODE = First Wins
    ATTR_ACCUM_MODE = Merge Clipper
    INSIDE -> Output_Inside (output)
    OUTSIDE -> GeometryValidator
    <REJECTED> -> Clipper__Rejected_
Output_Inside (output)
Note: Kontrollera så att objekten har geometri
GeometryValidator
    ARC_ENDPOINT_TOLERANCE_MODE = Auto
    NULL_REMOVAL = NULL_REMOVAL
    ISSUE_ATTR_NAME = _issues
    NAN_REMOVAL = NAN_REMOVAL
    TYPE_REPAIR = TYPE_REPAIR
    REPAIR = Yes
    SUMMARY = Detailed
    PRESETS = Basic Geometry Integrity
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    AREA_ORIENTATION = AREA_ORIENTATION
    ORIENTATION_CHECK_DIR = Valid
    CONNECT_Z_MODE_TR = First Wins
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    OFFSET = $(OFFSET)
    CORNER_STYLE = Round
    ANGLE = 1
    CAP_STYLE = Round
    BUFFERED -> SurfaceFootprintReplacer
    BUFFERED -> Bufferer_Buffered
Bufferer_Buffered: Inspector [off]
SurfaceFootprintReplacer
    SHADOW_MODE = Overhead Shadow
    OFFSET_Z = $(_ZMINVAL)
    FOOTPRINT -> Extruder
Note: Extrude 3 el 2 m
Extruder
    DISTANCE = $(DISTANCE)
    DIRECTION = Auto
    EXTRUDED -> Extruder_Extruded
    EXTRUDED -> Clipper [CLIPPER]
    <REJECTED> -> Extruder__Rejected_
Extruder_Extruded: Inspector
Extruder__Rejected_: Inspector

FME custom transformer CreateBasisBYA

Parameters:
- IFC_UNIQUE_ID = @Value(ifc_unique_id)   # Ifc Unique Id

Bookmark: BasisBYA
Input_storey (input)
    -> MinZ_2
MinZ_2
    -> SurfaceFootprintReplacer_3
SurfaceFootprintReplacer_3
    SHADOW_MODE = Overhead Shadow
    OFFSET_Z = @Value(_zminval)
    FOOTPRINT -> Dissolver_2
Input_pointCloud (input)
    -> MinZ
Input_facade (input)
    -> MinZ
MinZ
    -> SurfaceFootprintReplacer_2
SurfaceFootprintReplacer_2
    SHADOW_MODE = Overhead Shadow
    OFFSET_Z = @Value(_zminval)
    FOOTPRINT -> HullAccumulator
    <REJECTED> -> SurfaceFootprintReplacer_2__Rejected_
HullAccumulator
    GROUP_BY = ifc_unique_id _zminval
    HULLTYPE_PARAM = Convex ()
    3DMODE_PARAM = 3D
    DEFAULTZ = @Value(_zminval)
    HULL -> Dissolver_2
Dissolver_2
    NO_OVRLP = No
    ACCUM_INPUT_ATTRS = Merge Incoming Attributes
    DEAGGREGATE_INPUT = Yes
    CONNECT_Z_MODE = Ignore
    AREA -> BoundsExtractor
BoundsExtractor
    YMAX = _ymax
    XMIN = _xmin
    XMAX = _xmax
    YMIN = _ymin
    ZMAX = _zmax
    ZMIN = _zmin
    -> SurfaceFootprintReplacer
SurfaceFootprintReplacer
    SHADOW_MODE = Overhead Shadow
    OFFSET_Z = @Value(_zmin)
    FOOTPRINT -> DonutHoleExtractor_2
DonutHoleExtractor_2
    DEAGGREGATE_INPUT = Yes
    OUTERSHELL -> Output (output)
Output (output)
SurfaceFootprintReplacer_2__Rejected_: Inspector [off]

FME custom transformer PointCloudClipper

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    GROUP_BY = ifc_unique_id
    ACCUM_ATTRS_NAME = Yes
    SPACING = 20
    EXTRACT_RASTER_NODATA_NAME = No
    ATTRS_TO_PRESERVE = ifc_parent_unique_id,String
    -> Clipper_2 [CLIPPEE]
Clipper (input)
    -> Clipper_2 [CLIPPER]
Clipper_2
    LINES_AS_SEGMENTS = No
    MEASURE_TYPE = Continuous
    CREATE_AGGREGATES = Yes
    BOUNDARY_CASES = Treat as Inside
    MISSING_VAL_MODE = Compute
    CLIPPED_ATTR = _clipped
    CLIP_TYPE = Single Clipper
    VAL_SOURCE = Clippee Only
    PRESERVE_CLIPPEE_EXTENTS = No
    INSIDE -> PointCloudCoercer
    INSIDE -> Output_3D (output)
PointCloudCoercer
    POINT_COMPONENTS_PRESERVE_DISPLAY = Attributes
    CONVERT_TO_DISPLAY = Individual Points
    ACCUM_ATTRS_NAME = Yes
    PART_NUMBER_ATTR_NAME = _part_number
    COERCED -> 2DForcer
2DForcer
    2D -> HullAccumulator
HullAccumulator
    GROUP_BY = ifc_unique_id
    HULLTYPE_PARAM = Convex ()
    3DMODE_PARAM = 2D
    HULL -> Output_2D (output)
Output_2D (output)
Output_3D (output)

FME custom transformer MinZ

Input (input)
    -> AttributeCreator
AttributeCreator
    ATTR_TABLE = SET_TO _zminval
    -> BoundsExtractor
BoundsExtractor
    YMAX = _ymax
    XMIN = _xmin
    XMAX = _xmax
    YMIN = _ymin
    ZMAX = _zmax
    ZMIN = _zmin
    -> PythonCaller
PythonCaller
    PYTHONSYMBOL = FeatureProcessor
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    -> Output (output)
Output (output)
