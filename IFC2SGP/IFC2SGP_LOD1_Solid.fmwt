FME workspace IFC2SGP_LOD1_Solid.fmwt
Title: IFC2SGP_LOD1_Solid
Description: This workspace is released under the 3-Clause BSD License. 
    Copyright (c) 2018, Lantmäteriet
    All rights reserved.
    Redistribution and use in source and binary forms, with or without modification, are permitted provided that the following conditions are met:
    1. Redistributions of source code must retain the above copyright notice, this list of conditions and the following disclaimer.
    2. Redistributions in binary form must reproduce the above copyright notice, this list of conditions and the following disclaimer in the documentation and/or other materials provided with the distribution.
    3. Neither the name of the copyright holder nor the names of its contributors may be used to endorse or promote products derived from this software without specific prior written permission.
    THIS SOFTWARE IS PROVIDED BY THE COPYRIGHT HOLDERS AND CONTRIBUTORS "AS IS" AND ANY EXPRESS OR IMPLIED WARRANTIES, INCLUDING, BUT NOT LIMITED TO, THE IMPLIED WARRANTIES OF MERCHANTABILITY AND FITNESS FOR A PARTICULAR PURPOSE ARE DISCLAIMED. IN NO EVENT SHALL THE COPYRIGHT HOLDER OR CONTRIBUTORS BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE. 
=-=-=-=-=-=-=-=-=
FME Workspace-fil framtagen av Svensk geoprocess Testdatateam, Lantmäteriet. Översätter byggnadsdata i SketchUp-format (*.skp) till XML-fil/filer (*.xml) enligt Svensk geoprocess geodataspecifikationer. Processen bygger på indata från Malmö stad.
    FME Workspace-filen är specifikt utformad för de indata som översätts. Detta innebär att i fallet då indata från annan källa ska översättas behövs sannolikt en modifiering av själva FME-processen för att passa indata i fråga.
    Bör öppnas med FME version 2017.1.2 eller nyare för att garantera att översättningen fungerar korrekt. 
Geodataspecifikation: 
http://www.lantmateriet.se/sv/Om-Lantmateriet/Samverkan-med-andra/Svensk-geoprocess/specifikationer-och-matningsanvisningar/
UML-modell: 
ftp://ftp.lantmateriet.se/pub/svensk_geoprocess/UML-modell/SvenskGeoprocess_HTML_modell/index.htm
XML-schema: 
http://namespace.lantmateriet.se/svenskgeoprocess/by/3.0/BY_Byggnad.xsd
Mer om testdata för Svensk geoprocess och möjlighet till validering av XML-fil/filer se: http://www.lantmateriet.se/sv/Om-Lantmateriet/Samverkan-med-andra/Svensk-geoprocess/testdata-och-validering/
Vid frågor eller synpunkter, kontakta supporten på svenskgeoprocess@lm.se.
=-=-=-=-=-=-=-=-=
www.lantmateriet.se
History: 2017-08-21,Lantmäteriet,Version 3.0 TEST 1; skapad,2018-01-29,Lantmäteriet,Version 3.0; uppdaterad till ny version,2018-02-08,Lantmäteriet,Version 3.0; ändrad axelordning för gml:lowerCorner och gml:upperCorner

Parameters:
- uttagDatum = 20180702100300   # Välj datum för uttag av datamängd ur lager
- DestDataset_TEXTLINE = $(FME_MF_DIR)BY_Byggnad_v3.0_KTH_solid_lod1.xml   # Destination Text File
- namnDatamängd = KTH demo   # Skriv in namn på datamängd
- dimension = 3   # Välj dimension
- koordinatsystemPlan = EPSG:3008   # Välj koordinatsystem i plan
- koordinatsystemPlanIdentifier = urn:ogc:def:crs:EPSG::3008   # Välj identifier för koordinatsystem i plan
- byggnadNamn = KTH demo   # " " byggnadNamn
- byggnadAndamal = verksamhet   # " " byggnadAndamal
- status = planerad   # " " status
- byggnadNummer = 201   # " " byggnadNummer
- bygglovAtgardTyp = nybyggnad   # " " bygglovAtgardTyp
- bygglovStatusTyp = slutbesked   # " " bygglovStatusTyp
- atgardAr_bygglovstatus = 2016-05-01T14:07:00+00:00   # " " atgardAr_bygglovstatus
- beslutsdatum_bygglovStatus = 2016-05-01T14:07:00+00:00   # " " beslutsdatum_bygglovStatus
- decimalPlaces = 2   # Decimal Places
- ofriGrund = false   # " " ofriGrund
- id_datamangd_versionId = 1   # " " id_datamangd_versionId
- id_byggnad_versionId = 1   # " " id_byggnad_versionId
- coClassID = 1HeRFbeBDBIuMgfcpC1nk_   # " " coClassID
- coClassKod = BV   # " " coClassKod
- SourceDataset_IFC = $(FME_MF_DIR)1/wb_template_1530612771254_3524/Demohuset_A_modell_130409_KTH.ifc   # Source Industry Foundation Class (IFC) File(s)
- planlagetyp = fasad   # " " planlagetyp
- hojdLage3DTopp = takets högsta punkt (nock)   # " " hojdLage3DTopp

Readers:
- IFC_1: IFC from $(SourceDataset_IFC)

Writers:
- TEXTLINE_1: TEXTLINE to $(DestDataset_TEXTLINE)

IfcSlab (reader IFC_1)
    attributes: GlobalId char(22), Name string, Description string, ObjectType string, Tag string, PredefinedType enumeration, Axis geometry, Body geometry
    -> StoreyIndexFinder [AttributeCreator_StoreyList_Input]
    -> CoordinateExtractor
    -> IfcSlab_-__FootprintAreaCalculator_All_ListBasedFeatureMerger
IfcSlab_-__FootprintAreaCalculator_All_ListBasedFeatureMerger: Junction
    -> FootprintAreaCalculator [IfSlab_Input]
    -> FootprintAreaCalculator [All_ListBasedFeatureMerger]
    -> FootprintAreaCalculator [Clipper_Max_3m_Input]
    -> FootprintAreaCalculator [Clipper_Max_5m_Input]
IfcBuildingStorey (reader IFC_1)
    attributes: GlobalId char(22), Name string, Description string, ObjectType string, LongName string, CompositionType enumeration, Elevation real, Axis geometry, Body geometry
    -> StoreyIndexFinder [PythonCaller_2_Input]
    -> FootprintAreaCalculator [BuildingStorey_AggregatedList]
Note: Copyright (c) 2018, Lantmäteriet / All rights reserved. / This workspace is released under the 3-Clause BSD License. For details, see the Description of this workspace. See also https://opensource.org/licenses/BSD-3-Clause
Note: Obs! Publika parametrar (från LMs original): / uttagDatum: Obligatorisk; värde väljs manuellt / namnDatamängd: Obligatorisk; värde väljs manuellt / dimension: Obligatorisk; värde väljs manuellt / koordinatsystemPlan: Obligatorisk; värde väljs manuellt / koordinatsystemPlanIdentifier: Obligatorisk; värde väljs manuellt
StoreyIndexFinder
    IFC_UNIQUE_ID = @Value(ifc_unique_id)
    storeyIndex = 3
    Tester_StoreyIndex_Passed -> SurfaceFootprintReplacer
Note: Adding attributes for max and / min Z to the footprint for later / extrusion.
PythonCaller_Z_limit_adder
    PYTHONSOURCE:
      import fme
      import fmeobjects
      import numpy

      # Template Class Interface:
      # When using this class, make sure its name is set as the value of
      # the 'Class or Function to Process Features' transformer parameter
      class FeatureProcessor(object):
          def __init__(self):
              self.featureList = []
              self.maxZ = None
              self.minZ = None

          def input(self,feature):
              if feature.getAttribute('_maxZBuilding'):
                  self.maxZ = float(feature.getAttribute('_maxZBuilding'))
                  self.minZ = float(feature.getAttribute('_minZBuilding'))
              else:
                  self.featureList.append(feature)

          def close(self):
              for f in self.featureList:
                  f.setAttribute('maxZBuilding', self.maxZ)
                  f.setAttribute('minZBuilding', self.minZ)
                  f.setAttribute('diffZBuilding', self.maxZ - self.minZ)

                  self.pyoutput(f)
    PYTHONSYMBOL = FeatureProcessor
    NEW_ATTRIBUTES = maxZBuilding minZBuilding diffZBuilding
    -> PythonCaller_Z_limit_adder_2
IfcWall (reader IFC_1)
    attributes: GlobalId char(22), Name string, Description string, ObjectType string, Tag string, Axis geometry, Body geometry
    -> IfcWall_-__FootprintAreaCalculator_Clipper_BottomEdge_Input
IfcWall_-__FootprintAreaCalculator_Clipper_BottomEdge_Input: Junction
    -> FootprintAreaCalculator [Clipper_BottomEdge_Input]
    -> FootprintAreaCalculator [Clipper_Max_5m_Input]
    -> FootprintAreaCalculator [Clipper_Max_3m_Input]
    -> FootprintAreaCalculator [All_ListBasedFeatureMerger]
FootprintAreaCalculator
    IFC_PARENT_ID = @Value(ifc_parent_id)
    ELEVATION = @Value(Elevation)
    IFC_PARENT_UNIQUE_ID = @Value(ifc_parent_unique_id)
    IFC_UNIQUE_ID = @Value(ifc_unique_id)
    FloorIndex = 1
    FootprintArea -> PythonCaller_Z_limit_adder_2
Note: Adding attribute for building area / and attribute to state that area exists.
PythonCaller_Z_limit_adder_2
    PYTHONSOURCE:
      import fme
      import fmeobjects
      import numpy

      # Template Class Interface:
      # When using this class, make sure its name is set as the value of
      # the 'Class or Function to Process Features' transformer parameter
      class FeatureProcessor(object):
          def __init__(self):
              self.featureList = []
              self.byArea = None

          def input(self,feature):
              if feature.getAttribute('_area'):
                  self.byArea = int(round(float(feature.getAttribute('_area'))))
              else:
                  self.featureList.append(feature)

          def close(self):
              for f in self.featureList:
                  f.setAttribute('byggnadsArea', self.byArea)
                  f.setAttribute('byAreaExists', 1)

                  self.pyoutput(f)
    PYTHONSYMBOL = FeatureProcessor
    NEW_ATTRIBUTES = byggnadsArea byAreaExists
    -> Rotator
UUIDGenerator_BDM
    UUID_ATTR = _uuid_BDM
    -> BY_BDM
Note: Ändrar datum-formatet / för attributet till ISO- / format.
DateTimeConverter
    REPAIR_INPUT = NO
    DATETIME_ATTR = _BDM_uttagDatum
    OUT_FORMAT = ISO
    -> StringConcatenator_8
AttributeKeeper_2
    KEEP_ATTRS = diffZBuilding,_maxZBuilding,maxZBuilding,byAreaExists,byggnadsArea
    -> AttributeCreator_RelativHojd
AttributeCreator_RelativHojd
    ATTR_TABLE:
      SET_TO relHojd = @Evaluate(@Value(diffZBuilding)*0.001)
      SET_TO hogstaHojd = takets högsta punkt (nock)
      SET_TO lagstaHojd = byggnadens lägsta punkt
    -> AttributeCreator_planlage_hojdLage3DTopp
Note: "Transformation" / The IFC models is "transformed" to SWEREF99 13 30 by rough rotation - scaling - translation.
AttributeCreator_planlage_hojdLage3DTopp
    ATTR_TABLE:
      SET_TO planLageTyp = $(planlagetyp)
      SET_TO hojdLage3DTopp = $(hojdLage3DTopp)
    -> AttributeRounder_2
AttributeRounder_2
    PLACES = 2
    ROUND_TYPE = Nearest
    SRC_ATTRS = relHojd
    -> UUIDGenerator_BD
Note: UUID for ByggadsDel
UUIDGenerator_BD
    UUID_ATTR = _uuid_BYD
    -> Extruder
    -> PythonCaller_WallCreator_2
    -> Offsetter_wallSurface
Note: To create 3D model
Extruder
    DISTANCE = @Value(relHojd)
    DIRECTION = Vertical
    EXTRUDED -> CoordinateSystemSetter
    EXTRUDED -> BoundsExtractor_2
CoordinateSystemSetter
    COORDSYS = $(koordinatsystemPlan)
    -> CoordinateRounder_2
CoordinateRounder_2
    YPREC = $(decimalPlaces)
    XPREC = $(decimalPlaces)
    ZPREC = $(decimalPlaces)
    ROUNDED -> GeometryExtractor_2
Note: To get "fake" serial ID for / different building parts.
Counter
    SCOPE = Local
    DOMAIN = counter
    START = 101
    CNT_ATTR = _count_bd
    -> StringConcatenator_12
UUIDGenerator_B
    UUID_ATTR = _uuid_B
    -> BY_B
BY_B_Output: Inspector
PythonCaller_WallCreator_2
    PYTHONSOURCE:
      import fme
      import fmeobjects
      from math import sqrt

      # Template Class Interface:
      # When using this class, make sure its name is set as the value of
      # the 'Class or Function to Process Features' transformer parameter
      class FeatureProcessor(object):
          def __init__(self):
              self.groundPoints = []

          def input(self,feature):
              self.groundPoints.append(feature)

          def close(self):
              # Looping over all building parts
              for byd in self.groundPoints:
                  roofHeight = float(byd.getAttribute('relHojd'))
                  uuidBYD = byd.getAttribute('_uuid_BYD')
                  po = byd.getGeometry()
                  cu = po.getBoundaryAsCurve()
                  li = cu.getAsLine()
                  points = li.getPoints()
                  coords = []
                  for co in points:
                      coords.append(co.getXYZ())

                  # Looping over the wall segments
                  for pos in xrange(len(coords)-1):
                      # Creating list with corner coords for current wall surface
                      tempPolyLineList = [coords[pos], coords[pos+1], (coords[pos+1][0], coords[pos+1][1], roofHeight), (coords[pos][0], coords[pos][1], roofHeight)]

                      tempPolyLine = fmeobjects.FMELine(tempPolyLineList)

                      tempWall = fmeobjects.FMEPolygon(tempPolyLine)

                      newFeatureWall = fmeobjects.FMEFeature()
                      newFeatureWall.setGeometry(tempWall)
                      newFeatureWall.setAttribute('_uuid_BYD', uuidBYD)
                      newFeatureWall.setAttribute('surfaceType', 'wall')
                      self.pyoutput(newFeatureWall)
    PYTHONSYMBOL = FeatureProcessor
    NEW_ATTRIBUTES = _uuid_BYD surfaceType
    -> UUIDGenerator_surfaces
Note: To "move" the footprint to roof height / to get a roof surface.
Offsetter_wallSurface
    MODE = Cartesian Coordinate
    ZOFF = @Value(relHojd)
    XOFF = 0
    YOFF = 0
    OFFSET -> AttributeCreator_surfaceType_roof_2
AttributeCreator_surfaceType_roof_2
    ATTR_TABLE = SET_TO surfaceType = roof
    -> UUIDGenerator_surfaces
UUIDGenerator_surfaces
    UUID_ATTR = _uuid_surface
    -> CoordinateSystemSetter_2
CoordinateSystemSetter_2
    COORDSYS = $(koordinatsystemPlan)
    -> CoordinateRounder
CoordinateRounder
    YPREC = $(decimalPlaces)
    XPREC = $(decimalPlaces)
    ZPREC = $(decimalPlaces)
    ROUNDED -> GeometryExtractor_3
GeometryExtractor_3
    OGCVERSION = 1.2
    OGC_WKT_PRECISION_DISPLAY = Shortened 64-bit
    OMIT_NAMESPACES_DISPLAY = No
    ATTR = _geometri_surface
    REMOVE_GEOMETRY = No
    PREFER_POLYGON_OVER_SURFACE = No
    OGEOSMS_URL_PREFIX = http://maps.google.com/?q=
    KIND_LONG = GML v3.2.1
    -> StringReplacer_9
StringReplacer_9
    FIND_TEXT = $(koordinatsystemPlan)
    REPLACE_TEXT = $(koordinatsystemPlanIdentifier)
    REGEXP = NO
    CASE = NO
    SRC_ATTRS = _geometri_surface
    NO_MATCH = _FME_NO_OP_
    -> UUIDGenerator_BY
UUIDGenerator_BY
    UUID_ATTR = _uuid_BY
    -> BY_BY
TestFilter
    DEFAULT_VALUE = <UNFILTERED>
    TEST_LIST = BOOL_OP,OR,COMPOSITE_TEST,<Unused>,TEST_CLAUSE,"TEST @Value(surfaceType) = roof",Tak,BOOL_OP,OR,COMPOSITE_TEST,<Unused>,TEST_CLAUSE,"TEST @Value(surfaceType) = wall",Vägg,BOOL_OP,OR,COMPOSITE_TEST,<Unused>,TEST_CLAUSE,"TEST @Value(surfaceType) = bottom",Botten
    Tak -> StringConcatenator_11
    Vägg -> StringConcatenator_10

Bookmark: Finding max and min Z-ccord of the building
  Used to get relative height (highest point of roof and lowest part of building) 
  and to extrude the footprint to a 3D solid.
CoordinateExtractor
    MODE = All Coordinates
    LIST_NAME = _indices
    -> ListRangeExtractor
ListRangeExtractor
    SRC_LIST = _indices{}.z
    MIN = _minZ
    MAX = _maxZ
    -> Aggregator
Aggregator
    ACCUM_ATTRS_NAME = Merge Incoming Attributes
    MODE = Geometry - Assemble One Level
    ORDERED = No
    SEP = ,
    AGGREGATE_TYPE = Homogeneous Collection (If Possible)
    LIST_NAME = _minMaxZList
    LIST_ATTRS_TO_INCLUDE = _maxZ _minZ
    AGGREGATE -> ListRangeExtractor_2
ListRangeExtractor_2
    SRC_LIST = _minMaxZList{}._maxZ
    MIN = _junk
    MAX = _maxZBuilding
    -> ListRangeExtractor_3
ListRangeExtractor_3
    SRC_LIST = _minMaxZList{}._minZ
    MIN = _minZBuilding
    MAX = _junk
    -> AttributeKeeper
AttributeKeeper
    KEEP_ATTRS = _maxZBuilding,_minZBuilding
    -> PythonCaller_Z_limit_adder

Bookmark: Creating simplified footprint
  Replaces the slab with it's footprint and dissolves to get oen polygon.
  Generalizing to remove small balconies etc. 
  The start and end of the permeter was in a dent of the outer wall and could not be removed by generaliazaion. To solve this a hard coded python script was added.
SurfaceFootprintReplacer
    SHADOW_MODE = Overhead Shadow
    LIGHT_Y = 0
    LIGHT_Z = 1
    OFFSET_Z = 0
    LIGHT_X = 0
    FOOTPRINT -> Dissolver_2
    <REJECTED> -> SurfaceFootprintReplacer__Rejected_
Dissolver_2
    CONNECT_Z_MODE = First Wins
    DEAGGREGATE_INPUT = Yes
    ACCUM_INPUT_ATTRS = Use Attributes From One Feature
    NO_OVRLP = No
    AREA -> PythonCaller_Coordinate_remover
    <REJECTED> -> Dissolver__Rejected_
PythonCaller_Coordinate_remover
    PYTHONSOURCE:
      import fme
      import fmeobjects
      import numpy

      # Template Class Interface:
      # When using this class, make sure its name is set as the value of
      # the 'Class or Function to Process Features' transformer parameter
      class FeatureProcessor(object):
          def __init__(self):
              self.featureList = []

          def input(self,feature):
                  self.featureList.append(feature)

          def close(self):
              for f in self.featureList:
                  coordIndex = range(2,21) # Here index 0,1,21 shall be removed
                  coordsIn = f.getAllCoordinates()
                  coordsOut = []
                  for i in coordIndex:
                      coordsOut.append(coordsIn[i])

                  tp = fmeobjects.FMELine(coordsOut)
                  tw = fmeobjects.FMEPolygon(tp)

                  nfw = fmeobjects.FMEFeature()
                  nfw.setGeometry(tw)

                  self.pyoutput(nfw)
    PYTHONSYMBOL = FeatureProcessor
    -> Generalizer
Generalizer
    PRESERVE = No
    TOLERANCE = 600
    ALG_TEXT = Douglas (Generalize)
    -> PythonCaller_Z_limit_adder
Dissolver__Rejected_: Inspector
SurfaceFootprintReplacer__Rejected_: Inspector

Bookmark: To SWEREF99 1330 coordinates
  Rotating, moving and scaling to get a roughly correct position of the building
Rotator
    XORIG = 0
    YORIG = 0
    ANGLE = -30
    ROTATED -> Scaler_2
Scaler_2
    ZSCALE = 0.001
    SCALE_ORIGIN = 0,0
    XSCALE = 0.001
    YSCALE = 0.001
    RASTER_SCALING = Extents
    TEXT_LOC_ONLY = Location and Size
    SCALED -> Offsetter
Offsetter
    MODE = Cartesian Coordinate
    ZOFF = 0
    XOFF = 113830
    YOFF = 6162760
    OFFSET -> BoundsExtractor_4
    OFFSET -> AttributeKeeper_2

Bookmark: Skapar attributen _upperCorner och _lowerCorner
  Only bounding box for datamängd in this case
BoundsExtractor_4
    ZMIN = _zmin
    XMIN = _xmin
    ZMAX = _zmax
    YMAX = _ymax
    XMAX = _xmax
    YMIN = _ymin
    -> AttributeRounder
Note: Round to two decimals
AttributeRounder
    PLACES = $(decimalPlaces)
    ROUND_TYPE = Nearest
    SRC_ATTRS = _ymin _zmax _ymax _xmin _xmax
    -> StringConcatenator_13
StringConcatenator_13
    VAL_ATTR = _upperCorner
    PARM_LINE = @Value(_ymax) @Value(_xmax)
    ACTION = Create New Attribute
    -> StringConcatenator_14
StringConcatenator_14
    VAL_ATTR = _lowerCorner
    PARM_LINE = @Value(_ymin) @Value(_xmin)
    ACTION = Create New Attribute
    -> UUIDGenerator_BDM

Bookmark: Attribut-kopplingar
  Kopplar attribut från indata till Svensk geoprocess-attribut. Detaljer kring Svensk geoprocess-attributen finns bl.a. i UML-modellen för Byggnad: ftp://ftp.lantmateriet.se/pub/svensk_geoprocess/UML-modell/SvenskGeoprocess_HTML_modell/index.htm
Note: BY_ByggnadDatamängd
BY_BDM: AttributeCreator
    ATTR_TABLE:
      SET_TO _BDM_lowerCorner = @Value(_lowerCorner)
      SET_TO _BDM_upperCorner = @Value(_upperCorner)
      SET_TO _BDM_id_localId = @Value(_uuid_BDM)
      SET_TO _BDM_id_namespace = SGP.BY
      SET_TO _BDM_id_versionId = $(id_datamangd_versionId)
      SET_TO _BDM_uttagDatum = $(uttagDatum)
      SET_TO _BDM_metadata
      SET_TO _BDM_koordinatsystemPlan = $(koordinatsystemPlan)
      SET_TO _BDM_hojdsystem
      SET_TO _BDM_dimension = $(dimension)
    -> DateTimeConverter
Note: Note that the attribute for geometry must be / changed depending on geometry type: / _BD_lod2_kropp = _geometri_BYD_solid / _BD_lod2_ytgeometri = _geometri_BYD_surface
Note: BY_Byggnadsdel
BY_BD: AttributeCreator
    ATTR_TABLE:
      SET_TO _BD_lowerCorner = @Value(_lowerCorner)
      SET_TO _BD_upperCorner = @Value(_upperCorner)
      SET_TO _BD_byggnadNummerDel
      SET_TO _BD_byggnadAndamalDel
      SET_TO _BD_statusDel
      SET_TO _BD_bygglovStatusDel
      SET_TO _BD_antalVaningarOverMark
      SET_TO _BD_antalVaningarUnderMark
      SET_TO _BD_absolutHojd
      SET_TO _BD_relativHojd = @Value(relHojd)
      SET_TO _BD_boAreaDel
      SET_TO _BD_heltUnderMark
      SET_TO _BD_byggnadKaraktarDel
      SET_TO _BD_takTyp
      SET_TO _BD_geometriLoD0
      SET_TO _BD_geometri3DLoD1 = @Value(_geometri_BYD_2)
      SET_TO _BD_lod1_hojdLage3DTopp = @Value(hojdLage3DTopp)
      SET_TO _BD_lod2_geometri
      SET_TO _BD_lod2_ytgeometri
      SET_TO _BD_lod2_kropp
      SET_TO _BD_lod2_terrangskarning
      SET_TO _BD_lod2_lagesosakerhetPlan
      SET_TO _BD_lod2_lagesosakerhetHojd
      SET_TO _BD_lod2_matmetodPlan
      SET_TO _BD_lod2_matmetodHojd
      SET_TO _BD_lod2_geometriskUpplosning
      SET_TO _BD_lod2_flyghojd
      SET_TO _BD_lod2_skalaUnderlag
      SET_TO _BD_lod2_tidpunktMatning
      SET_TO _BD_lod2_osakertLage
      SET_TO _BD_lod2_osakertLageAnledning
      SET_TO _BD_lod2_ansvarigOrganisation
      SET_TO _BD_lod2_utforandeOrganisation
      SET_TO _BD_lod2_HMK_Standardniva
      SET_TO _BD_lod2_foljerMatningsanvisning
      SET_TO _BD_lod2_aktualitet
      SET_TO _BD_lod2_hojdLage3DBotten
      SET_TO _BD_lod2_planLageTyp
      SET_TO _BD_geometri3DLoD3
      SET_TO _BD_externReferens
      SET_TO _BD_cc_coClassId
      SET_TO _BD_cc_coClassKod
    -> Counter
Note: BY_Byggnad
BY_B: AttributeCreator
    ATTR_TABLE:
      SET_TO _B_lowerCorner = @Value(_lowerCorner)
      SET_TO _B_upperCorner = @Value(_upperCorner)
      SET_TO _B_id_localId = @Value(_uuid_B)
      SET_TO _B_id_namepace = SGP.BY
      SET_TO _B_id_versionId = $(id_byggnad_versionId)
      SET_TO _B_beginLifeSpanVersion
      SET_TO _B_endLifeSpanVersion
      SET_TO _B_byggnadNummer = $(byggnadNummer)
      SET_TO _B_byggnadAndamal = $(byggnadAndamal)
      SET_TO _B_byggnadNamn = $(byggnadNamn)
      SET_TO _B_status = $(status)
      SET_TO _B_bygglovAtgardTyp = $(bygglovAtgardTyp)
      SET_TO _B_bygglovStatusTyp = $(bygglovStatusTyp)
      SET_TO _B_beslutsdatum = $(beslutsdatum_bygglovStatus)
      SET_TO _B_atgardAr = $(atgardAr_bygglovstatus)
      SET_TO _B_byggnadArea = @Value(byggnadsArea)
      SET_TO _B_boArea
      SET_TO _B_byggnadKaraktar
      SET_TO _B_byggnadAnmarkning
      SET_TO _B_undantagenFranAdressattning
      SET_TO _B_ofriGrund = $(ofriGrund)
      SET_TO _B_externReferens
      SET_TO _B_cc_coClassId = $(coClassID)
      SET_TO _B_cc_coClassKod = $(coClassKod)
    -> StringConcatenator
    -> BY_B_Output
Note: BY_Begransningsyta
BY_BY: AttributeCreator
    ATTR_TABLE:
      SET_TO _BY_lowerCorner
      SET_TO _BY_upperCorner
      SET_TO _BY_id_localId = @Value(_uuid_BY)
      SET_TO _BY_id_namespace = SGP.BY
      SET_TO _BY_id_versionId
      SET_TO _BY_beginLifespanVersion
      SET_TO _BY_endLifespanVersion
      SET_TO _BY_geometri = @Value(_geometri_surface)
      SET_TO _BY_geometriMetadata
      SET_TO _BY_externReferens
      SET_TO _BY_cc_coClassId
      SET_TO _BY_cc_coClassKod
    -> TestFilter
Note: BY_AggregeradByggnad
BY_AB: AttributeCreator [off]
    ATTR_TABLE:
      SET_TO _AB_lowerCorner
      SET_TO _AB_upperCorner
      SET_TO _AB_id_localId
      SET_TO _AB_id_namespace
      SET_TO _AB_id_versionId
      SET_TO _AB_beginLifespanVersion
      SET_TO _AB_endLifespanVersion
      SET_TO _AB_geometriAggregeradByggnad
      SET_TO _AB_externReferens
      SET_TO _AB_cc_coClassId
      SET_TO _AB_cc_coClassKod
Note: BY_FysiskByggnad
BY_FB: AttributeCreator [off]
    ATTR_TABLE:
      SET_TO _FB_lowerCorner
      SET_TO _FB_upperCorner
      SET_TO _FB_id_localId
      SET_TO _FB_id_namespace
      SET_TO _FB_id_versionId
      SET_TO _FB_beginLifespanVersion
      SET_TO _FB_endLifespanVersion
      SET_TO _FB_geometriFysiskByggnad
      SET_TO _FB_externReferens
      SET_TO _FB_cc_coClassId
      SET_TO _FB_cc_coClassKod
Note: BY_Byggnadstillbehör
BY_BT: AttributeCreator [off]
    ATTR_TABLE:
      SET_TO _BT_lowerCorner
      SET_TO _BT_upperCorner
      SET_TO _BT_id_localId
      SET_TO _BT_id_namespace
      SET_TO _BT_id_versionId
      SET_TO _BT_beginLifespanVersion
      SET_TO _BT_endLifespanVersion
      SET_TO _BT_byggnadstillbehor
      SET_TO _BT_status
      SET_TO _BT_lod0_punktgeometri
      SET_TO _BT_lod0_ytgeometri
      SET_TO _BT_lod0_lagesosakerhetPlan
      SET_TO _BT_lod0_lagesosakerhetHojd
      SET_TO _BT_lod0_matmetodPlan
      SET_TO _BT_lod0_matmetodHojd
      SET_TO _BT_lod0_geometriskUpplosning
      SET_TO _BT_lod0_flyghojd
      SET_TO _BT_lod0_skalaUnderlag
      SET_TO _BT_lod0_tidpunktMatning
      SET_TO _BT_lod0_osakertLage
      SET_TO _BT_lod0_osakertLageAnledning
      SET_TO _BT_lod0_ansvarigOrganisation
      SET_TO _BT_lod0_utforandeOrganisation
      SET_TO _BT_lod0_HMK_Standardniva
      SET_TO _BT_lod0_foljerMatningsanvisning
      SET_TO _BT_lod0_aktualitet
      SET_TO _BT_lod0_planLageTyp
      SET_TO _BT_lod0_hojdLageTyp
      SET_TO _BT_geometri3DLoD3
      SET_TO _BT_externReferens
      SET_TO _BT_cc_coClassId
      SET_TO _BT_cc_coClassKod
Note: BY_Oppning
BY_O: AttributeCreator [off]
    ATTR_TABLE:
      SET_TO _O_lowerCorner
      SET_TO _O_upperCorner
      SET_TO _O_id_localId
      SET_TO _O_id_namespace
      SET_TO _O_id_versionId
      SET_TO _O_beginLifespanVersion
      SET_TO _O_endLifespanVersion
      SET_TO _O_geometri
      SET_TO _O_geometriMetadata
      SET_TO _O_externReferens
      SET_TO _O_cc_coClassId
      SET_TO _O_cc_coClassKod

Bookmark: Skapar GML-ID
StringConcatenator_8
    VAL_ATTR = _gml_id_BDM
    PARM_LINE = @Value(_BDM_id_namespace).@Value(_BDM_id_localId)
    ACTION = Create New Attribute
    -> XMLTemplater [ROOT]
StringConcatenator_12
    VAL_ATTR = _gml_id_BD
    PARM_LINE = SGP.BY.@Value(_uuid_BYD)
    ACTION = Create New Attribute
    -> XMLTemplater_4 [BY_BYGGNADSDEL]
StringConcatenator
    VAL_ATTR = _gml_id_B
    PARM_LINE = @Value(_B_id_namepace).@Value(_B_id_localId)
    ACTION = Create New Attribute
    -> XMLTemplater_4 [ROOT]
StringConcatenator_11
    VAL_ATTR = _gml_id_BYTY
    PARM_LINE = @Value(_BY_id_namespace).@Value(_BY_id_localId)
    ACTION = Create New Attribute
    -> XMLTemplater [BY_TAKYTA]
StringConcatenator_10
    VAL_ATTR = _gml_id_BYVY
    PARM_LINE = @Value(_BY_id_namespace).@Value(_BY_id_localId)
    ACTION = Create New Attribute
    -> XMLTemplater [BY_VAGGYTA]

Bookmark: Extracting and adjusting geometry (Byggnadsdel)
  The string replaces replacing "&lt;" and "&lr;" with "<" and ">" from the XML templater
GeometryExtractor_2
    OGCVERSION = 1.2
    OGC_WKT_PRECISION_DISPLAY = Shortened 64-bit
    OMIT_NAMESPACES_DISPLAY = No
    ATTR = _geometri_BYD
    REMOVE_GEOMETRY = No
    PREFER_POLYGON_OVER_SURFACE = No
    OGEOSMS_URL_PREFIX = http://maps.google.com/?q=
    KIND_LONG = GML v3.2.1
    -> StringReplacer_6
StringReplacer_6
    FIND_TEXT = $(koordinatsystemPlan)
    REPLACE_TEXT = $(koordinatsystemPlanIdentifier)
    REGEXP = NO
    CASE = NO
    SRC_ATTRS = _geometri_BYD
    NO_MATCH = _FME_NO_OP_
    -> XMLTemplater_kropp [ROOT]
XMLTemplater_kropp
    VISIBLE_QUERY_VALIDATE = Yes
    RESULT_ATTRIBUTE = _geometri_BYD_2
    OUTPUT_XML_HEADER = No
    ROOT_QUERY_EXPR:
      <by:kropp xmlns:by="http://namespace.lantmateriet.se/svenskgeoprocess/by/3.0">
          {fme:get-attribute("_geometri_BYD")}
      </by:kropp>
    -> StringReplacer_4
StringReplacer_4
    FIND_TEXT = &lt;
    REPLACE_TEXT = <
    REGEXP = NO
    CASE = NO
    SRC_ATTRS = _geometri_BYD_2
    NO_MATCH = _FME_NO_OP_
    -> StringReplacer_5
StringReplacer_5
    FIND_TEXT = &gt;
    REPLACE_TEXT = >
    REGEXP = NO
    CASE = NO
    SRC_ATTRS = _geometri_BYD_2
    NO_MATCH = _FME_NO_OP_
    -> BoundsExtractor_3

Bookmark: Skapar attributen _upperCorner och _lowerCorner
  Byggnad, not included in this version
BoundsExtractor_3
    ZMIN = _zmin
    XMIN = _xmin
    ZMAX = _zmax
    YMAX = _ymax
    XMAX = _xmax
    YMIN = _ymin
    -> AttributeRounder_4
Note: Round to two decimals
AttributeRounder_4
    PLACES = $(decimalPlaces)
    ROUND_TYPE = Nearest
    SRC_ATTRS = _ymin _zmax _ymax _xmin _xmax
    -> StringConcatenator_4
StringConcatenator_4
    VAL_ATTR = _upperCorner
    PARM_LINE = @Value(_ymax) @Value(_xmax)
    ACTION = Create New Attribute
    -> StringConcatenator_5
StringConcatenator_5
    VAL_ATTR = _lowerCorner
    PARM_LINE = @Value(_ymin) @Value(_xmin)
    ACTION = Create New Attribute
    -> BY_BD

Bookmark: Skapar attributen _upperCorner och _lowerCorner
  Byggnad, not included in this version
BoundsExtractor_2
    ZMIN = _zmin
    XMIN = _xmin
    ZMAX = _zmax
    YMAX = _ymax
    XMAX = _xmax
    YMIN = _ymin
    -> AttributeRounder_3
Note: Round to two decimals
AttributeRounder_3
    PLACES = $(decimalPlaces)
    ROUND_TYPE = Nearest
    SRC_ATTRS = _ymin _zmax _ymax _xmin _xmax
    -> StringConcatenator_2
StringConcatenator_2
    VAL_ATTR = _upperCorner
    PARM_LINE = @Value(_ymax) @Value(_xmax)
    ACTION = Create New Attribute
    -> StringConcatenator_3
StringConcatenator_3
    VAL_ATTR = _lowerCorner
    PARM_LINE = @Value(_ymin) @Value(_xmin)
    ACTION = Create New Attribute
    -> UUIDGenerator_B

Bookmark: Genererar XML-fil (utbytesfil)
Note: Kopplar attribut till en / XML-kod. XML-koden har / genererats från schemat / BY_Byggnad.xsd och / består av BY_Byggnad / och BY_Byggnadsdel.
XMLTemplater_4
    VISIBLE_QUERY_VALIDATE = Yes
    BY_BYGGNADSDEL_QUERY_EXPR:

                                  <by:bestarAv>
                                      <by:BY_Byggnadsdel gml:id="{fme:get-attribute("_gml_id_BD")}">
                                          <by:byggnadNummerDel>{fme:get-attribute("_count_bd")}</by:byggnadNummerDel>
                                          <by:relativHojd>
                                              <by:hogstaHojdLageTyp>{fme:get-attribute("hogstaHojd")}</by:hogstaHojdLageTyp>
                                              <by:lagstaHojdLageTyp>{fme:get-attribute("lagstaHojd")}</by:lagstaHojdLageTyp>
                                              <by:hojdvarde>{fme:get-attribute("_BD_relativHojd")}</by:hojdvarde>
                                          </by:relativHojd>
                                          <by:heltUnderMark xsi:nil="true" nilReason="unknown"/>
                                          <by:geometri3DLoD1>
                                              {fme:get-attribute("_BD_geometri3DLoD1")}
                                              <by:geometriMetadata xsi:nil="true" nilReason="unknown"/>
      										<by:hojdLage3DBotten xsi:nil="true" nilReason="unknown"/>
      										<by:planLageTyp>{fme:get-attribute("planLageTyp")}</by:planLageTyp>
                                              <by:hojdLage3DTopp>{fme:get-attribute("_BD_lod1_hojdLage3DTopp")}</by:hojdLage3DTopp>
                                          </by:geometri3DLoD1>
                                      </by:BY_Byggnadsdel>
                                  </by:bestarAv>
    GROUP_BY = _uuid_BYD
    RESULT_ATTRIBUTE = _XMLDelKod
    OUTPUT_XML_HEADER = No
    ROOT_QUERY_EXPR:
      					<by:bestarAv xmlns:ad="http://inspire.ec.europa.eu/schemas/ad/4.0" xmlns:base="http://inspire.ec.europa.eu/schemas/base/3.3" xmlns:base2="http://inspire.ec.europa.eu/schemas/base2/2.0" xmlns:bu-base="http://inspire.ec.europa.eu/schemas/bu-base/4.0" xmlns:by="http://namespace.lantmateriet.se/svenskgeoprocess/by/3.0" xmlns:gco="http://www.isotc211.org/2005/gco" xmlns:ge="http://namespace.lantmateriet.se/svenskgeoprocess/base/ge/3.0" xmlns:gmd="http://www.isotc211.org/2005/gmd" xmlns:gml="http://www.opengis.net/gml/3.2" xmlns:gn="http://inspire.ec.europa.eu/schemas/gn/4.0" xmlns:gsr="http://www.isotc211.org/2005/gsr" xmlns:gss="http://www.isotc211.org/2005/gss" xmlns:gts="http://www.isotc211.org/2005/gts" xmlns:sg="http://namespace.lantmateriet.se/svenskgeoprocess/base/sg/3.0" xmlns:sgk="http://namespace.lantmateriet.se/svenskgeoprocess/base/sgk/3.0" xmlns:sgk1="http://namespace.lantmateriet.se/svenskgeoprocess/base/sgk/3.2" xmlns:xlink="http://www.w3.org/1999/xlink" xmlns:xml="http://www.w3.org/XML/1998/namespace" xmlns:xsi="http://www.w3.org/2001/XMLSchema-instance">
      						<by:BY_Byggnad gml:id="{fme:get-attribute("_gml_id_B")}">
      							<sg:id>
      								<base:localId>{fme:get-attribute("_B_id_localId")}</base:localId>
      								<base:namespace>{fme:get-attribute("_B_id_namepace")}</base:namespace>
                                      <base:versionId>{fme:get-attribute("_B_id_versionId")}</base:versionId>
      							</sg:id>
      							<sg:beginLifespanVersion xsi:nil="true" nilReason="unknown"/>
      							<by:byggnadNummer>{fme:get-attribute("_B_byggnadNummer")}</by:byggnadNummer>
                                  <by:byggnadAndamal>
                                      <by:byggnadAndamalTyp>{fme:get-attribute("_B_byggnadAndamal")}</by:byggnadAndamalTyp>
                                  </by:byggnadAndamal>
                                  <by:byggnadNamn>
                                      <sg:namn>{fme:get-attribute("_B_byggnadNamn")}</sg:namn>
                                      <sg:namnstatus>föreslaget namn</sg:namnstatus>
                                      <sg:sprak>svenska</sg:sprak>
                                      <sg:externalReference nilReason="unknown" xsi:nil="true"/>
                                  </by:byggnadNamn>
      							<by:status>{fme:get-attribute("_B_status")}</by:status>
                                  <by:bygglovStatus>
                                      <by:bygglovAtgardTyp>{fme:get-attribute("_B_bygglovAtgardTyp")}</by:bygglovAtgardTyp>
                                      <by:bygglovStatusTyp>{fme:get-attribute("_B_bygglovStatusTyp")}</by:bygglovStatusTyp>
                                      <by:beslutsdatum>{fme:get-attribute("_B_beslutsdatum")}</by:beslutsdatum>
                                      <by:atgardAr>{fme:get-attribute("_B_atgardAr")}</by:atgardAr>
                                  </by:bygglovStatus>
                                  { if( fme:has-attribute("byAreaExists") )
                                      then <by:byggnadArea>{fme:get-attribute("_B_byggnadArea")}</by:byggnadArea>
                                      else ()
                                  }
                                  <by:ofriGrund>{fme:get-attribute("_B_ofriGrund")}</by:ofriGrund>
                                  <by:coClass>
                                      <sg:coClassId>{fme:get-attribute("_B_cc_coClassId")}</sg:coClassId>
                                      <sg:coClassKod>{fme:get-attribute("_B_cc_coClassKod")}</sg:coClassKod>
                                  </by:coClass>
                                  {fme:process-features("BY_BYGGNADSDEL")}
      						</by:BY_Byggnad>
      					</by:bestarAv>
    CONSECUTIVE_GROUPS = No
    -> StringReplacer_7
StringReplacer_7
    FIND_TEXT = &lt;
    REPLACE_TEXT = <
    REGEXP = NO
    CASE = NO
    SRC_ATTRS = _XMLDelKod
    NO_MATCH = _FME_NO_OP_
    -> StringReplacer_8
StringReplacer_8
    FIND_TEXT = &gt;
    REPLACE_TEXT = >
    REGEXP = NO
    CASE = NO
    SRC_ATTRS = _XMLDelKod
    NO_MATCH = _FME_NO_OP_
    -> XMLTemplater [BY_BYGGNAD]
Note: Kopplar attribut till en / XML-kod. XML-koden har / genererats från schemat / BY_Byggnad.xsd.
XMLTemplater
    BY_BYGGNAD_QUERY_EXPR = {fme:get-attribute("_XMLDelKod")}
    BY_TAKYTA_QUERY_EXPR:
      	<by:bestarAv>
      		<by:BY_Takyta gml:id="{fme:get-attribute("_gml_id_BYTY")}">
      			<sg:id>
      				<base:localId>{fme:get-attribute("_BY_id_localId")}</base:localId>
      				<base:namespace>{fme:get-attribute("_BY_id_namespace")}</base:namespace>
      			</sg:id>
      			<sg:beginLifespanVersion xsi:nil="true" nilReason="unknown"/>
      			<by:geometri>
          			{fme:get-attribute("_BY_geometri")}
      			</by:geometri>
      			<by:begransarByggnadsdel xlink:href="#SGP.BY.{fme:get-attribute('_uuid_BYD')}"/>
      		</by:BY_Takyta>
      	</by:bestarAv>
    OUTPUT_XML_HEADER = No
    RESULT_ATTRIBUTE = _result
    ROOT_QUERY_EXPR:
      <?xml version="1.0" encoding="UTF-8"?>
      <by:BY_ByggnadDatamangd gml:id="{fme:get-attribute("_gml_id_BDM")}" xmlns:ad="http://inspire.ec.europa.eu/schemas/ad/4.0" xmlns:base="http://inspire.ec.europa.eu/schemas/base/3.3" xmlns:base2="http://inspire.ec.europa.eu/schemas/base2/2.0" xmlns:bu-base="http://inspire.ec.europa.eu/schemas/bu-base/4.0" xmlns:by="http://namespace.lantmateriet.se/svenskgeoprocess/by/3.0" xmlns:gco="http://www.isotc211.org/2005/gco" xmlns:ge="http://namespace.lantmateriet.se/svenskgeoprocess/base/ge/3.0" xmlns:gmd="http://www.isotc211.org/2005/gmd" xmlns:gml="http://www.opengis.net/gml/3.2" xmlns:gn="http://inspire.ec.europa.eu/schemas/gn/4.0" xmlns:gsr="http://www.isotc211.org/2005/gsr" xmlns:gss="http://www.isotc211.org/2005/gss" xmlns:gts="http://www.isotc211.org/2005/gts" xmlns:sg="http://namespace.lantmateriet.se/svenskgeoprocess/base/sg/3.0" xmlns:sgk="http://namespace.lantmateriet.se/svenskgeoprocess/base/sgk/3.0" xmlns:sgk1="http://namespace.lantmateriet.se/svenskgeoprocess/base/sgk/3.2" xmlns:xlink="http://www.w3.org/1999/xlink" xmlns:xml="http://www.w3.org/XML/1998/namespace" xmlns:xsi="http://www.w3.org/2001/XMLSchema-instance" xsi:schemaLocation="http://namespace.lantmateriet.se/svenskgeoprocess/by/3.0 http://namespace.lantmateriet.se/svenskgeoprocess/by/3.0/BY_Byggnad.xsd">
      	<gml:boundedBy>
      		<gml:Envelope srsName="urn:ogc:def:crs:EPSG::3008" srsDimension="2">
      			<gml:lowerCorner>{fme:get-attribute("_BDM_lowerCorner")}</gml:lowerCorner>
      			<gml:upperCorner>{fme:get-attribute("_BDM_upperCorner")}</gml:upperCorner>
      		</gml:Envelope>
      	</gml:boundedBy>
      	<sg:id>
      		<base:localId>{fme:get-attribute("_BDM_id_localId")}</base:localId>
      		<base:namespace>{fme:get-attribute("_BDM_id_namespace")}</base:namespace>
              <base:versionId>{fme:get-attribute("_BDM_id_versionId")}</base:versionId>
      	</sg:id>
      	<sg:uttagDatum>{fme:get-attribute("_BDM_uttagDatum")}</sg:uttagDatum>
      	<sg:koordinatsystemPlan>{fme:get-attribute("_BDM_koordinatsystemPlan")}</sg:koordinatsystemPlan>
      	<sg:dimension>{fme:get-attribute("_BDM_dimension")}</sg:dimension>
          {fme:process-features("BY_BYGGNAD")}
          {fme:process-features("BY_TAKYTA")}
          {fme:process-features("BY_VAGGYTA")}
      </by:BY_ByggnadDatamangd>
    VISIBLE_QUERY_VALIDATE = Yes
    BY_VAGGYTA_QUERY_EXPR:
      	<by:bestarAv>
      		<by:BY_Vaggyta gml:id="{fme:get-attribute("_gml_id_BYVY")}">
      			<sg:id>
      				<base:localId>{fme:get-attribute("_BY_id_localId")}</base:localId>
      				<base:namespace>{fme:get-attribute("_BY_id_namespace")}</base:namespace>
      			</sg:id>
      			<sg:beginLifespanVersion xsi:nil="true" nilReason="unknown"/>
      			<by:geometri>
          			{fme:get-attribute("_BY_geometri")}
      			</by:geometri>
      			<by:begransarByggnadsdel xlink:href="#SGP.BY.{fme:get-attribute('_uuid_BYD')}"/>
      		</by:BY_Vaggyta>
      	</by:bestarAv>
    -> StringReplacer
StringReplacer
    FIND_TEXT = &lt;
    REPLACE_TEXT = <
    REGEXP = NO
    CASE = NO
    SRC_ATTRS = _result
    NO_MATCH = _FME_NO_OP_
    -> StringReplacer_2
StringReplacer_2
    FIND_TEXT = &gt;
    REPLACE_TEXT = >
    REGEXP = NO
    CASE = NO
    SRC_ATTRS = _result
    NO_MATCH = _FME_NO_OP_
    -> XMLFormatter
XMLFormatter
    COLLAPSE_EMPTY_ELEMENT = Yes
    SCHEMALOC_CLEANUP = No
    NAMESPACE_CLEANUP = Yes
    OUTPUT_ENCODING = utf-8
    XML_INPUT_TYPE = Attribute Specifying XML Text
    REMOVE_ALL_COMMENT = No
    XML_OUTPUT_ATTR = text_line_data
    FORMATTING_CHOICE = Pretty-Print XML
    WHITESPACE_HANDLING = Preserve all whitespace
    REMOVE_EMPTY_ELEMENT = No
    XML_ATTR_TEXT = _result
    INDENT_SIZE = 1
    LIST_NAME = _xml_error
    XML_OUTPUT_TYPE = Attribute
    REPLACE_TABS_WITH_SPACES = no
    TEXT_INDENT = no
    PASSED -> HTTPCaller
Note: Hämtar schemat / BY_Byggnad.xsd / Version 3.0 från dess / plats på webben.
HTTPCaller
    CONNECTION_TIMEOUT_LENGTH = 60
    TARGET_URL = http://namespace.lantmateriet.se/svenskgeoprocess/by/3.0/BY_Byggnad.xsd
    ERROR_ATTR = _error
    SAVE_FILE = Attribute
    TRANSFER_TIMEOUT_LENGTH = 90
    TARGET_ATTR = _xml_schema
    USE_COOKIES = No
    HTTP_METHOD = GET
    FOLLOW_REDIRECTS = Yes
    VERIFY_SSL_CERTIFICATES = Yes
    TARGET_ATTR_ENCODING = auto-detect
    STATUS_CODE_ATTR = _http_status_code
    RESPONSE_HEADER_LIST_ATTR = _headers
    -> XMLValidator
Note: Validerar XML-filen / mot schemat.
XMLValidator
    XML_INPUT_TYPE = Attribute Specifying XML Text
    SCHEMA_LOC = @Value(_xml_schema)
    LIST_NAME = _XML_schemafelmeddelande
    VAL_MODE_1 = Syntax and Schema
    XML_ATTR_TEXT = text_line_data
    LIMIT_ERRORS = No
    PASSED -> text_line (writer TEXTLINE_1)
    FAILED -> XMLValidator_Failed
    FAILED -> text_line (writer TEXTLINE_1)
Note: Skriver ut koden till en XML-fil / med filändelsen *.xml
text_line (writer TEXTLINE_1)
    attributes: text_line_data buffer
Note: Inspektera fel i listan kallad / "_XML_schemafelmeddelande"
XMLValidator_Failed: Inspector

FME custom transformer MinZ

Input (input)
    -> AttributeCreator
AttributeCreator
    ATTR_TABLE = SET_TO _zminval
    -> BoundsExtractor
BoundsExtractor
    ZMIN = _zmin
    XMIN = _xmin
    ZMAX = _zmax
    YMAX = _ymax
    XMAX = _xmax
    YMIN = _ymin
    -> PythonCaller
PythonCaller
    PYTHONSOURCE:
      import fme
      import fmeobjects
      # Template Function interface:
      # When using this function, make sure its name is set as the value of
      # the 'Class or Function to Process Features' transformer parameter
      def processFeature(feature):
          pass

      def minZval(list):
          logger = fmeobjects.FMELogFile()
          tempminz = float('inf')
          for f in list:
              temp = f.getAttribute("_zmin")
              logger.logMessageString('LOGG MESSAGE')
              logger.logMessageString(str(temp))
              logger.logMessageString(str(tempminz))
              if  temp < tempminz:
                  tempminz = temp

          return tempminz

      # Template Class Interface:
      # When using this class, make sure its name is set as the value of
      # the 'Class or Function to Process Features' transformer parameter
      class FeatureProcessor(object):
          def __init__(self):
              self.featureList  = []

          def input(self,feature):
              self.featureList.append(feature)

          def close(self):
              minz = minZval(self.featureList)
              for f in self.featureList:
                  f.setAttribute('_zminval', minz)
                  self.pyoutput(f)
    PYTHONSYMBOL = FeatureProcessor
    -> Output (output)
Output (output)

FME custom transformer FootprintAreaCalculator

Parameters:
- IFC_PARENT_UNIQUE_ID = @Value(ifc_parent_unique_id)   # Ifc Parent Unique Id
- IFC_UNIQUE_ID = @Value(ifc_unique_id)   # ifc_unique_id
- ELEVATION = @Value(Elevation)   # Elevation
- IFC_PARENT_ID = @Value(ifc_parent_id)   # Ifc Parent Id
- FloorIndex = 1   # First floor index

All_ListBasedFeatureMerger (input)
    -> ListBasedFeatureMerger [SUPPLIER]
IfSlab_Input (input)
    -> StoreyIndexFinder_2 [AttributeCreator_StoreyList_Input]
BuildingStorey_AggregatedList (input)
    -> StoreyIndexFinder_2 [PythonCaller_2_Input]
StoreyIndexFinder_2
    IFC_UNIQUE_ID = @Value(ifc_unique_id)
    storeyIndex = $(FloorIndex)
    Tester_StoreyIndex_Passed -> CreateBasisBYA [Input_storey]
    Tester_StoreyIndex_Passed -> StoreyIndexFinder_FirstFloor
StoreyIndexFinder_FirstFloor: Inspector
Note: Clip the building to be able to find the protruding parts.
Clipper_Max_3m_Input (input)
    -> Clipper_Max_3m_2
Clipper_Max_5m_Input (input)
    -> Clipper_Max_5m_3
Clipper_BottomEdge_Input (input)
    -> Clipper_BottomEdge_2
Note: Clip lowest part of the wall
Clipper_BottomEdge_2: Building_Clipper
    DISTANCE = 10
    IFC_PARENT_UNIQUE_ID = @Value(ifc_parent_unique_id)
    OFFSET_Z = @Value(Elevation)
    Output_extruded -> PointCloudClipper [Clipper]
    Output_clipper -> CreateBasisBYA [Input_facade]
    Rejected -> PointCloudClipper [Wall]
Note: Handle wall objects that won't clip with default FME Clipper
PointCloudClipper
    IFC_PARENT_UNIQUE_ID = @Value(ifc_parent_unique_id)
    IFC_UNIQUE_ID = @Value(ifc_unique_id)
    Output_2D -> CreateBasisBYA [Input_pointCloud]
CreateBasisBYA
    IFC_UNIQUE_ID = @Value(ifc_unique_id)
    -> AttributeManager_2
    -> Protruding_Part [Bufferer_Input]
    -> SurfaceFootprintReplacer_3
SurfaceFootprintReplacer_3
    SHADOW_MODE = Overhead Shadow
    OFFSET_Z = 0
    FOOTPRINT -> Snapper
Note: Calculate BUA, / scale from mm2 to m2
AreaCalculator
    AREA_TYPE = Plane Area
    MULT = 1/1000000
    AREA_ATTR = _area
    -> AttributeRounder
Note: Round to on dec.
AttributeRounder
    PLACES = 1
    ROUND_TYPE = Nearest
    SRC_ATTRS = _area
    -> AttributeKeeper_2
AttributeKeeper_2
    KEEP_ATTRS = _area
    -> FootprintArea (output)
FootprintArea (output)

Bookmark: Klipper byggnaden 0-3 m
Clipper_Max_3m_2: Building_Clipper
    DISTANCE = 3000
    IFC_PARENT_UNIQUE_ID = @Value(ifc_parent_unique_id)
    OFFSET_Z = @Value(Elevation)
    Output_extruded -> PointCloudClipper_5 [Clipper]
    Output_clipper -> Protruding_Part [Clipper_Byggnad]
    Rejected -> PointCloudClipper_5 [Wall]
PointCloudClipper_5
    IFC_PARENT_UNIQUE_ID = @Value(ifc_parent_unique_id)
    IFC_UNIQUE_ID = @Value(ifc_unique_id)
    Output_3D -> Protruding_Part [Clipper_Byggnad]

Bookmark: Klipper byggnaden 3-5 m
Clipper_Max_5m_3: Building_Clipper
    DISTANCE = 2000
    IFC_PARENT_UNIQUE_ID = @Value(ifc_parent_unique_id)
    OFFSET_Z = @Value(Elevation)+3000
    Output_extruded -> PointCloudClipper_6 [Clipper]
    Output_clipper -> Protruding_Part_2 [Clipper_Byggnad]
    Rejected -> PointCloudClipper_6 [Wall]
PointCloudClipper_6
    IFC_PARENT_UNIQUE_ID = @Value(ifc_parent_unique_id)
    IFC_UNIQUE_ID = @Value(ifc_unique_id)
    Output_3D -> Protruding_Part_2 [Clipper_Byggnad]

Bookmark: 0-3m, < 0,5m
Protruding_Part
    DISTANCE = 3000
    OFFSET = 500
    _ZMIN = @Value(_zmin)
    _ZMINVAL = @Value(_zminval)
    Output_Outside -> Aggregator

Bookmark: 3-5m, < 1,5m
Note: Flytta zmin +3000mm
AttributeManager_2
    ATTR_TABLE:
      SET_TO _zminval = @Value(_zminval)+3000
      SET_TO _zmin = +3000
    -> Protruding_Part_2 [Bufferer_Input]
Protruding_Part_2
    DISTANCE = 2000
    OFFSET = 1500
    _ZMIN = @Value(_zmin)
    _ZMINVAL = @Value(_zminval)
    Output_Outside -> Aggregator

Bookmark: Protruding parts
Note: Clip protruding parts (Output_Outside)
Aggregator
    ACCUM_ATTRS_NAME = Merge Incoming Attributes
    MODE = Attributes Only
    ORDERED = No
    SEP = ,
    CONCAT_ATTRS = ifc_unique_id
    LIST_NAME = ListName
    LIST_ATTRS_TO_INCLUDE = ifc_unique_id
    AGGREGATE -> ListElementCounter
ListElementCounter
    LIST_NAME = ListName{}
    CNT_ATTR = nbrStoreys
    -> ListBasedFeatureMerger [REQUESTOR]
Note: Retrive the whole protruding object with ifc_unique_id, project and merge with "BasisBUA"
ListBasedFeatureMerger
    MERGE_TYPE = Geometry
    BUILD_INCOMPLETE = Merge Supplier Information
    MODE = AUTO
    GEOM_TYPE = Build Aggregates
    REFEEATTR = @Value(ifc_unique_id)
    PROCESS_DUPS = Yes
    REFERATTR = ListName{}.ifc_unique_id
    MERGED -> SurfaceFootprintReplacer_2
SurfaceFootprintReplacer_2
    SHADOW_MODE = Overhead Shadow
    OFFSET_Z = 0
    FOOTPRINT -> Snapper
Dissolver_2
    CONNECT_Z_MODE = First Wins
    DEAGGREGATE_INPUT = Yes
    ACCUM_INPUT_ATTRS = Use Attributes From One Feature
    NO_OVRLP = No
    AREA -> AreaCalculator

Bookmark: Prepare for dissolve
  Snapp areas that won't dissolve (because they don't intersect/ are connected)
Snapper
    CLEANING_TOLERANCE_MODE = AUTO
    TOLERANCE = 10
    SNAPTYPE_PARAM = Segment Snapping
    SNAPPED -> Dissolver_2
    UNTOUCHED -> Dissolver_2

FME custom transformer Protruding_Part

Parameters:
- _ZMINVAL = @Value(_zminval)   # Zminval
- OFFSET = 500   # Buffer Amount
- DISTANCE = 3000   # Distance
- _ZMIN = @Value(_zmin)   # Zmin

Bufferer_Input (input)
    -> Bufferer
Clipper_Byggnad (input)
    -> Clipper [CLIPPEE]
Clipper
    BOUNDARY_CASES = Treat as Inside
    CONNECT_Z_MODE = First Wins
    CLIP_TYPE = Multiple Clippers
    MISSING_VAL_MODE = Compute
    MEASURE_TYPE = Continuous
    ATTR_CONFLICT_RES = Use Clippee
    PRESERVE_CLIPPEE_EXTENTS = No
    LINES_AS_SEGMENTS = No
    ATTR_ACCUM_MODE = Merge Clipper
    CREATE_AGGREGATES = Yes
    DEFAULT_VAL = 0
    CLIPPED_ATTR = _clipped
    VAL_SOURCE = Clippee Only
    INSIDE -> Output_Inside (output)
    OUTSIDE -> GeometryValidator
    <REJECTED> -> Clipper__Rejected_
Output_Inside (output)
Note: Kontrollera så att objekten har geometri
GeometryValidator
    NAN_REMOVAL = NAN_REMOVAL
    SUMMARY = Detailed
    NULL_REMOVAL = NULL_REMOVAL
    ARC_ENDPOINT_TOLERANCE_MODE = Auto
    TYPE_REPAIR = TYPE_REPAIR
    ISSUE_ATTR_NAME = _issues
    PRESETS = Basic Geometry Integrity
    ORIENTATION_CHECK_DIR = Valid
    AREA_ORIENTATION = AREA_ORIENTATION
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%SHELL_VALIDATION_PARAMS%"Yes"%SOLID_VOID_REPAIR%""%"Yes"%OGC_SIMPLE_CHECK%""%"No"%OGC_VALID_CHECK%OGC_VALID_PARAMS%"No"%MISSING_TEXTURE_COORDINATES%""%"Yes"%MISSING_VERTEX_NORMALS%""%"Yes"%AREA_ORIENTATION%ORIENTATION_CHECK_PARAMS%"Yes"
    CONNECT_Z_MODE_TR = First Wins
    REPAIR = Yes
    PASSED -> Output_Outside (output)
    FAILED -> GeometryValidator_Failed
Output_Outside (output)
GeometryValidator_Failed: Inspector
Clipper__Rejected_: Inspector

Bookmark: Solider
  Skapa solider som sedan ska klippas med byggnaden för att hitta utkragande delar.
Note: Buffer 0,5m el 1,5m
Bufferer
    OFFSET = $(OFFSET)
    CAP_STYLE = Round
    ANGLE = 1
    CORNER_STYLE = Round
    BUFFERED -> SurfaceFootprintReplacer
    BUFFERED -> Bufferer_Buffered
Bufferer_Buffered: Inspector [off]
SurfaceFootprintReplacer
    SHADOW_MODE = Overhead Shadow
    OFFSET_Z = @Value(_zminval)
    FOOTPRINT -> Extruder
Note: Extrude 3 el 2 m
Extruder
    DISTANCE = $(DISTANCE)
    DIRECTION = Auto
    EXTRUDED -> Clipper [CLIPPER]
    EXTRUDED -> Extruder_Extruded
    <REJECTED> -> Extruder__Rejected_
Extruder_Extruded: Inspector
Extruder__Rejected_: Inspector

FME custom transformer CreateBasisBYA

Parameters:
- IFC_UNIQUE_ID = @Value(ifc_unique_id)   # Ifc Unique Id

Bookmark: BasisBYA
Input_storey (input)
    -> MinZ_2
MinZ_2
    -> SurfaceFootprintReplacer_3
SurfaceFootprintReplacer_3
    SHADOW_MODE = Overhead Shadow
    OFFSET_Z = @Value(_zminval)
    FOOTPRINT -> Snapper
Input_pointCloud (input)
    -> MinZ
Input_facade (input)
    -> MinZ
MinZ
    -> SurfaceFootprintReplacer_2
SurfaceFootprintReplacer_2
    SHADOW_MODE = Overhead Shadow
    OFFSET_Z = @Value(_zminval)
    FOOTPRINT -> HullAccumulator
    <REJECTED> -> SurfaceFootprintReplacer_2__Rejected_
HullAccumulator
    GROUP_BY = ifc_unique_id _zminval
    DEFAULTZ = @Value(_zminval)
    3DMODE_PARAM = 3D
    HULLTYPE_PARAM = Convex ()
    HULL -> Snapper
Dissolver_2
    CONNECT_Z_MODE = Extend
    DEAGGREGATE_INPUT = Yes
    ACCUM_INPUT_ATTRS = Merge Incoming Attributes
    NO_OVRLP = No
    AREA -> BoundsExtractor
BoundsExtractor
    ZMIN = _zmin
    XMIN = _xmin
    ZMAX = _zmax
    YMAX = _ymax
    XMAX = _xmax
    YMIN = _ymin
    -> SurfaceFootprintReplacer
SurfaceFootprintReplacer
    SHADOW_MODE = Overhead Shadow
    OFFSET_Z = @Value(_zminval)
    FOOTPRINT -> DonutHoleExtractor_2
DonutHoleExtractor_2
    DEAGGREGATE_INPUT = Yes
    OUTERSHELL -> Output (output)
Output (output)
SurfaceFootprintReplacer_2__Rejected_: Inspector [off]

Bookmark: Prepare for dissolve
  Snapp areas that won't dissolve (because they don't intersect/ are connected)
Snapper
    CLEANING_TOLERANCE_MODE = AUTO
    TOLERANCE = 10
    SNAPTYPE_PARAM = Segment Snapping
    SNAPPED -> Dissolver_2
    UNTOUCHED -> Dissolver_2

FME custom transformer PointCloudClipper

Parameters:
- IFC_UNIQUE_ID = @Value(ifc_unique_id)   # Ifc Unique Id
- IFC_PARENT_UNIQUE_ID = @Value(ifc_parent_unique_id)   # Ifc Parent Unique Id

Note: Skapar ett punktmoln av de väggar som inte går igenom clippern. / Klipper punktmolnet, gör punktmolnet 2D och gör convexhull som skapar en polygon.
Note: 7/3 mha Mikael
Wall (input)
    -> PointCloudCombiner
PointCloudCombiner
    GROUP_BY = ifc_unique_id
    ATTRS_TO_PRESERVE = ifc_parent_unique_id,String
    ACCUM_ATTRS_NAME = Yes
    SPACING = 20
    EXTRACT_RASTER_NODATA_NAME = No
    -> Clipper_2 [CLIPPEE]
Clipper (input)
    -> Clipper_2 [CLIPPER]
Clipper_2
    BOUNDARY_CASES = Treat as Inside
    CLIP_TYPE = Single Clipper
    MISSING_VAL_MODE = Compute
    MEASURE_TYPE = Continuous
    PRESERVE_CLIPPEE_EXTENTS = No
    LINES_AS_SEGMENTS = No
    CREATE_AGGREGATES = Yes
    CLIPPED_ATTR = _clipped
    VAL_SOURCE = Clippee Only
    INSIDE -> PointCloudCoercer
    INSIDE -> Output_3D (output)
PointCloudCoercer
    CONVERT_TO_DISPLAY = Individual Points
    PART_NUMBER_ATTR_NAME = _part_number
    ACCUM_ATTRS_NAME = Yes
    POINT_COMPONENTS_PRESERVE_DISPLAY = Attributes
    COERCED -> 2DForcer
2DForcer
    2D -> HullAccumulator
HullAccumulator
    GROUP_BY = ifc_unique_id
    3DMODE_PARAM = 2D
    HULLTYPE_PARAM = Convex ()
    HULL -> Output_2D (output)
Output_2D (output)
Output_3D (output)

FME custom transformer StoreyIndexFinder

Parameters:
- storeyIndex = 3   # Test Parameter
- IFC_UNIQUE_ID = @Value(ifc_unique_id)   # Ifc Unique Id

Note: Connect to ListElementCounter / belonging to IfcBuildingStorey
PythonCaller_2_Input (input)
    -> Aggregator_2
Aggregator_2
    ACCUM_ATTRS_NAME = Merge Incoming Attributes
    MODE = Attributes Only
    ORDERED = No
    SEP = ,
    CONCAT_ATTRS = ifc_unique_id
    LIST_NAME = buildingStoreysID
    LIST_ATTRS_TO_INCLUDE = ifc_unique_id
    AGGREGATE -> ListElementCounter
ListElementCounter
    LIST_NAME = buildingStoreysID{}
    CNT_ATTR = nbrStoreys
    -> PythonCaller_2
Note: Connect to UUID creator for the walls
AttributeCreator_StoreyList_Input (input)
    -> AttributeCreator_StoreyList
AttributeCreator_StoreyList
    ATTR_TABLE = SET_TO storeyListIndex
    -> PythonCaller_2
PythonCaller_2
    PYTHONSOURCE:
      import fme
      import fmeobjects
      # Template Function interface:
      # When using this function, make sure its name is set as the value of
      # the 'Class or Function to Process Features' transformer parameter
      def processFeature(feature):
          pass


      def listFinder(f):
          pos = 0 # Index in list
          while pos < len(f):
              attList = f[pos].getAllAttributeNames()
              for att in attList:
                  if 'buildingStoreysID' in att:
                      return f[pos].getAttribute('buildingStoreysID{}.ifc_unique_id')
              pos += 1
          return None

      def storeyIndexFinder(fe,storeyList):
          # Returns the index in the storey list of current feature
          parentID = fe.getAttribute('ifc_parent_unique_id')
          pos = 0
          while pos < len(storeyList):
              if storeyList[pos] == parentID:
                  return pos
              pos += 1

      # Template Class Interface:
      # When using this class, make sure its name is set as the value of
      # the 'Class or Function to Process Features' transformer parameter
      class FeatureProcessor(object):
          def __init__(self):
              self.featureList = []

          def input(self,feature): # This function is called every time a feature is added
              self.featureList.append(feature)

          def close(self):
              li = listFinder(self.featureList) # Returns dict with key:uuid; value:maxX
              for f in self.featureList:
                  currIndex = storeyIndexFinder(f, li)
                  if currIndex:
                      f.setAttribute("storeyListIndex", currIndex)
                      self.pyoutput(f)
    PYTHONSYMBOL = FeatureProcessor
    NEW_ATTRIBUTES = storeyListIndex
    -> Tester_StoreyIndex
Note: Which storey index to include
Tester_StoreyIndex
    TEST_CLAUSE = TEST @Value(storeyListIndex) = $(storeyIndex)
    TEST_MODE = Automatic
    BOOL_OP = OR
    TEST_DESCRIPTION = ""
    PASSED -> Tester_StoreyIndex_Passed (output)
Tester_StoreyIndex_Passed (output)

FME custom transformer Building_Clipper

Parameters:
- IFC_PARENT_UNIQUE_ID = @Value(ifc_parent_unique_id)   # Ifc Parent Unique Id
- DISTANCE = 10   # Distance
- OFFSET_Z = 0   # Z" Elevation

Input (input)
    -> Deaggregator
    -> BoundsExtractor
    -> BoundingBoxAccumulator
    -> Input
BoundingBoxAccumulator
    DESTINATION_SCALE = 1
    SOURCE_SCALE = 1
    ACCUM_ATTRS_NAME = Use Attributes From One Feature
    ATTR_NAME = _topferIndex
    TOPFER_INDEX = No
    BOUNDING_BOX -> FeatureMerger [REQUESTOR]
BoundsExtractor
    ZMIN = _zmin
    XMIN = _xmin
    ZMAX = _zmax
    YMAX = _ymax
    XMAX = _xmax
    YMIN = _ymin
    -> ListBuilder
ListBuilder
    GROUPS_ORDERED = No
    LIST_NAME = _list
    LIST_ATTRS_TO_INCLUDE = _zmin ifc_parent_unique_id
    -> ListRangeExtractor
ListRangeExtractor
    SRC_LIST = _list{}._zmin
    MIN = _min
    MAX = _max
    -> FeatureMerger [SUPPLIER]
FeatureMerger
    MERGE_TYPE = Attributes Only
    SUPPLIERS_FIRST = No
    REJECT_NULL_MISSING_KEYS = No
    ATTR_CONFLICT_RES = Use Requestor
    ATTR_ACCUM_MODE = Merge Supplier
    PROCESS_DUPS = No
    IGNORE_NULLS = No
    JOIN_KEYS = @Value(ifc_parent_unique_id) @Value(_list{0}.ifc_parent_unique_id) AUTO
    MERGED -> SurfaceFootprintReplacer
SurfaceFootprintReplacer
    SHADOW_MODE = Overhead Shadow
    OFFSET_Z = $(OFFSET_Z)+@Value(_min)
    FOOTPRINT -> Extruder
Extruder
    DISTANCE = $(DISTANCE)
    DIRECTION = Vertical
    EXTRUDED -> Clipper_2 [CLIPPER]
    EXTRUDED -> Output_extruded (output)
Output_extruded (output)
Deaggregator
    GEOM_NAME_FIELD = _geometry_name
    CHILD_ID_ATTR = _hierarchy_child_id_list
    MODE = Flatten One Level
    PART_NUMBER_FIELD = _part_number
    SPLIT_COMPOSITES = No
    ID_SELECTION = ID and Parent ID
    COPY_ATTR = Every Node
    ID_ATTR = _hierarchy_id
    LIST_ATTR_MODE_LOOKUP = LEAN
    PARENT_ID_ATTR = _hierarchy_parent_id
    EXPLODE_INSTANCES = No
    DEAGGREGATED -> GeometryFilter
GeometryFilter
    GEOM_PORT_NAMES = Solid
    BREAK_AGG = No
    SOLID -> Clipper_2 [CLIPPEE]
Clipper_2
    BOUNDARY_CASES = Treat as Inside
    CLIP_TYPE = Multiple Clippers
    MISSING_VAL_MODE = Compute
    MEASURE_TYPE = Continuous
    PRESERVE_CLIPPEE_EXTENTS = No
    LINES_AS_SEGMENTS = No
    CREATE_AGGREGATES = Yes
    CLIPPED_ATTR = _clipped
    VAL_SOURCE = Clippee Only
    INSIDE -> Output_clipper (output)
    <REJECTED> -> Rejected (output)
Output_clipper (output)
Rejected (output)
Input: Inspector [off]
